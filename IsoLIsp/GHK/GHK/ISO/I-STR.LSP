(defun i-ystr(/ flglen piplen flgwidth pt1 pt2 ang ang1 pt3 pt3a pt3b
                pt4 pt4a pt4b pt4c pt4d pt5 pta pt5b pt6 pt6a pt6b pt6c
                pt6d pt7 pt7a pt7b ang-1 ang-2 pt7c pt7d pt8 pt8a pt8b
                pt8c pt9 pt9a pt10 pt10b pt10a)
    (setiso1)
    (setq c_item "STRY")
    (setq c_itemno "170")
    (sc1)
    (set-selec i-ystr1)
    (setiso2)
    (setq old_sd sd)
    (if (or (= sd "SW") (= sd "SCR'D"))(val-acc1)(if (= sd "BW")(val-acc2)(val-acc)))
    (prin1)
)
(defun i-ystr1()
    (if (= job_direc 2)(progn (i-gas)(i-blt)))
    (setq c_item "STRY")
    (setq c_itemno "170")
    (sc1)
    (i-straner)
    (if (or (= sd "SW") (= sd "SCR'D"))
        (setq pt2 (POLAR pt1 ang (* 13 sk1)))
        (setq pt2 (POLAR pt1 ang (* 20 sk1)))
    )
    (setq pt3 pt1)
    (setq pt3b(POLAR pt3 ang1 flglen))
    (setq pt3a(POLAR pt3 (+ ang1 (dtr 180)) flglen))
    (setq pt4 (POLAR pt1 ang (- piplen (* flgwidth 3))))
    (setq pt4a(POLAR pt4 (+ ang1 (dtr 180)) flglen))
    (setq pt4b(POLAR pt4 ang1 flglen))
    (setq pt4c(POLAR pt4 (+ ang1 (dtr 180)) piplen))
    (setq pt4d(POLAR pt4 ang1 piplen))
    (setq pt5 pt2)
    (setq pt5b(POLAR pt5 ang1 flglen))
    (setq pt5a(POLAR pt5 (+ ang1 (dtr 180)) flglen))
    (setq pt6 (POLAR pt2 (+ ang (dtr 180)) (- piplen (* flgwidth 3))))
    (setq pt6b(POLAR pt6 ang1 flglen))
    (setq pt6a(POLAR pt6 (+ ang1 (dtr 180)) flglen))
    (setq pt6d(POLAR pt6 ang1 piplen))
    (setq pt6c(POLAR pt6 (+ ang1 (dtr 180)) piplen))
    (setq pt7 (POLAR pt4 ang (* flglen 0.1)))
    (setq pt7a(POLAR pt4 ang (* flglen 0.64)))
    (setq pt7b(POLAR pt4 ang (* flglen 1.2)))
    (cond
        ((or (and (= (rtos ang 2 4) (rtos (dtr 30) 2 4)) (= (rtos ang1 2 4) (rtos (dtr 270) 2 4))) (and (= (rtos ang 2 4) (rtos (dtr 90) 2 4)) (= (rtos ang1 2 4) (rtos (dtr 330) 2 4))))
            (setq ang-1 75)
            (setq ang-2 165)
        )
        ((or (and (= (rtos ang 2 4) (rtos (dtr 330) 2 4)) (= (rtos ang1 2 4) (rtos (dtr 270) 2 4))) (and (= (rtos ang 2 4) (rtos (dtr 90) 2 4)) (= (rtos ang1 2 4) (rtos (dtr 30) 2 4))))
            (setq ang-1 15)
            (setq ang-2 105)
        )
        ((or (and (= (rtos ang 2 4) (rtos (dtr 210) 2 4)) (= (rtos ang1 2 4) (rtos (dtr 270) 2 4))) (and (= (rtos ang 2 4) (rtos (dtr 270) 2 4)) (= (rtos ang1 2 4) (rtos (dtr 330) 2 4))))
            (setq ang-1 -11)
            (setq ang-2 -101)
        )
        ((or (and (= (rtos ang 2 4) (rtos (dtr 150) 2 4)) (= (rtos ang1 2 4) (rtos (dtr 270) 2 4))) (and (= (rtos ang 2 4) (rtos (dtr 270) 2 4)) (= (rtos ang1 2 4) (rtos (dtr 30) 2 4))))
            (setq ang-1 -70)
            (setq ang-2 -160)
        )
        (T
            (setq ang-1 22)
            (setq ang-2 63)
        )
    )
    (setq pt7c(POLAR pt7   (+ ang1 (dtr ang-1)) (* piplen 1.2)))
    (setq pt7d(POLAR pt7b  (+ ang1 (dtr ang-1)) (* piplen 1.2)))
    (setq pt8a(POLAR pt7d  (+ ang1 (dtr ang-1)) (+ flglen (* 2 sk1))))
    (setq pt8 (POLAR pt8a  (+ ang1 (dtr (+ 180 ang-2))) (- (* piplen 2) (* 1 sk1))))
    (setq pt8b(POLAR pt8   (+ ang1 (dtr (+ 180 ang-2))) (- flglen piplen (* 0.5 sk1))))
    (setq pt8c(POLAR pt8a  (+ ang1 (dtr ang-2)) (- flglen piplen (* 0.5 sk1))))
    (setq pt9 (POLAR pt8b  (+ ang1 (dtr ang-1)) (* flgwidth 2)))
    (setq pt9a(POLAR pt9   (+ ang1 (dtr ang-2)) (- (* flglen 2) (* 2 sk1))))
    (setq pt10(POLAR pt9   (+ ang1 (dtr ang-1)) (* flgwidth 2)))
    (setq pt10b(POLAR pt10 (+ ang1 (dtr ang-2)) (- flglen (* 1 sk1))))
    (setq pt10a(POLAR pt10b (+ ang1 (dtr ang-2)) (- flglen (* 1 sk1))))
    (command "pline" pt3a "w" "0" "0" pt3b pt4b pt4a "c")
    (command "pline" pt5a "w" "0" "0" pt5b pt6b pt6a "c")
    (command "pline" pt8b "w" "0" "0" pt10 pt10a pt8c "c")
    (command "line" pt4c pt6c "" "line" pt4d pt6d "" "line" pt7c pt8 ""
             "line" pt7d pt8a "" "line" pt9 pt9a "")
    (if (= future 1)
        (if (/= dwgtype "D")(bmlist (POLAR pt1 ang1 flglen)))
    )
    (i-straner1)
)

(defun i-bstr(/ flglen piplen flgwidth pt1 pt2 pt2a ang ang1 pt3 pt3a pt3b
                pt4 pt4a pt4b pt4c pt4d pt5 pt5a pt5b pt5c pt5d pt5e
                pt5f pt5g pt6 pt6a pt6b pt7 pt7a pt7b pt7c pt7d pt8 pt8a pt8b
                pt8c pt8d pt8e pt8f pt8g)
    (setiso1)
    (setq c_item "STRB")
    (setq c_itemno "170")
    (sc1)
    (set-selec i-bstr1)
    (setiso2)
    (setq old_sd sd)
    (if (or (= sd "SW") (= sd "SCR'D"))(val-acc1)(if (= sd "BW")(val-acc2)(val-acc)))
    (prin1)
)

(defun i-bstr1()
    (if (= job_direc 2)(progn (i-gas)(i-blt)))
    (setq c_item "STRB")
    (setq c_itemno "170")
    (sc1)
    (i-straner)
    (if (or (= sd "SW") (= sd "SCR'D"))
        (progn
            (setq pt2 (POLAR pt1 ang (* 15 sk1)))
            (setq pt2a (POLAR pt1 ang (* 7.5 sk1)))
        )
        (progn
            (setq pt2 (POLAR pt1 ang (* 24 sk1)))
            (setq pt2a (POLAR pt1 ang (* 12 sk1)))
        )
    )
    (setq pt3 pt1)
    (setq pt3a(POLAR pt3 (+ ang1 (dtr 180)) flglen))
    (setq pt3b(POLAR pt3 ang1 flglen))
    (setq pt4 (POLAR pt1 ang (- piplen (* flgwidth 3))))
    (setq pt4a(POLAR pt4 (+ ang1 (dtr 180)) flglen))
    (setq pt4b(POLAR pt4 ang1 flglen))
    (setq pt4c(POLAR pt4 (+ ang1 (dtr 180)) piplen))
    (setq pt4d(POLAR pt4 ang1 piplen))
    (setq pt5 (POLAR pt2a (+ ang (dtr 180)) flglen))
    (setq pt5a(POLAR pt5 (+ ang1 (dtr 180)) piplen))
    (setq pt5b(POLAR pt5 ang1 piplen))
    (setq pt5c(POLAR pt5 (+ ang1 (dtr 180)) (* flglen 2)))
    (setq pt5d(POLAR pt5 ang1 (* flglen 2)))
    (setq pt5e(POLAR pt5c (+ ang (dtr 180)) (- flglen piplen)))
    (setq pt5f(POLAR pt5e (+ ang1 (dtr 180)) (* flgwidth 4)))
    (setq pt5g(POLAR pt5f (+ ang1 (dtr 180)) (* flgwidth 4)))
    (setq pt6 pt2)
    (setq pt6a(POLAR pt6 (+ ang1 (dtr 180)) flglen))
    (setq pt6b(POLAR pt6 ang1 flglen))
    (setq pt7 (POLAR pt2 (+ ang (dtr 180)) (- piplen (* flgwidth 3))))
    (setq pt7a(POLAR pt7 (+ ang1 (dtr 180)) flglen))
    (setq pt7b(POLAR pt7 ang1 flglen))
    (setq pt7c(POLAR pt7 (+ ang1 (dtr 180)) piplen))
    (setq pt7d(POLAR pt7 ang1 piplen))
    (setq pt8 (POLAR pt2a ang flglen))
    (setq pt8a(POLAR pt8 (+ ang1 (dtr 180)) piplen))
    (setq pt8b(POLAR pt8 ang1 piplen))
    (setq pt8c(POLAR pt8 (+ ang1 (dtr 180)) (* flglen 2)))
    (setq pt8d(POLAR pt8 ang1 (* flglen 2)))
    (setq pt8e(POLAR pt8c ang (- flglen piplen)))
    (setq pt8f(POLAR pt8e (+ ang1 (dtr 180)) (* flgwidth 4)))
    (setq pt8g(POLAR pt8f (+ ang1 (dtr 180)) (* flgwidth 4)))
    (command "layer" "s" "2c" "")
    (command "pline" pt3a "w" "0" "0" pt3b pt4b pt4a "c")
    (command "pline" pt6a "w" "0" "0" pt6b pt7b pt7a "c")
    (command "pline" pt5e "w" "0" "0" pt5g pt8g pt8e "c")
    (command "line" pt4c pt5a "" "line" pt4d pt5b "" "line" pt7c pt8a ""
             "line" pt7d pt8b "" "line" pt5f pt8f ""
             "line" pt5c pt5d pt8d pt8c ""
    )
    (command "arc" pt5d "e" pt8d "r" (* flglen 2))
    (if (= future 1)
        (if (/= dwgtype "D")(bmlist (POLAR pt1 (+ ang1 (dtr 180)) flglen)))
    )
    (command "layer" "s" "1c" "")
    (command "line" (POLAR pt2a ang1 (* flglen 2.5)) (POLAR pt2a (+ ang1  (dtr 180)) (* flglen 3)) "")
    (i-straner1)
)

(defun i-tstr(/ flglen piplen flgwidth pt1 pt2 ang ang1 pt3 pt3a pt3b
                pt4 pt4a pt4b pt4c pt4d pt5 pt5a pt5b pt5c pt5d
                pt6a pt6b pt7a pt7b pt8 pt8a pt8b pt9 pt9a pt9b pt9c
                pt9d pt10a pt10b)
    (setiso1)
    (setq c_item "STRT")
    (setq c_itemno "170")
    (sc1)
    (set-selec i-tstr1)
    (setiso2)
    (setq old_sd sd)
    (if (or (= sd "SW") (= sd "SCR'D"))(val-acc1)(if (= sd "BW")(val-acc2)(val-acc)))
    (prin1)
)
(defun i-tstr1()
    (if (= job_direc 2)(progn (i-gas)(i-blt)))
    (setq c_item "STRT")
    (setq c_itemno "170")
    (sc1)
    (i-straner)
    (if (or (= sd "SW") (= sd "SCR'D"))
        (progn
            (setq pt2 (POLAR pt1 ang (* 8 sk1)))
            (setq pt2a (POLAR pt1 ang (* 6 sk1)))
        )
        (progn
            (setq pt2 (POLAR pt1 ang (* 15 sk1)))
            (setq pt2a (POLAR pt1 ang (* 10 sk1)))
        )
    )
    (setq pt3 pt1)
    (setq pt3a(POLAR pt3 ang1 flglen))
    (setq pt3b(POLAR pt3 (+ ang1 (dtr 180)) flglen))
    (setq pt4 (POLAR pt1 ang (- piplen (* flgwidth 3))))
    (setq pt4a(POLAR pt4 ang1 flglen))
    (setq pt4b(POLAR pt4 (+ ang1 (dtr 180)) flglen))
    (setq pt4c(POLAR pt4 ang1 piplen))
    (setq pt4d(POLAR pt4 (+ ang1 (dtr 180)) piplen))
    (setq pt5 pt2)
    (setq pt5a(POLAR pt5 ang1 flglen))
    (setq pt5b(POLAR pt5 (+ ang1 (dtr 180)) flglen))
    (setq pt5c(POLAR pt5 ang1 piplen))
    (setq pt5d(POLAR pt5 (+ ang1 (dtr 180)) piplen))
    (setq pt6a(POLAR pt5a ang (* flgwidth 4)))
    (setq pt6b(POLAR pt5b ang (* flgwidth 4)))
    (setq pt7a(POLAR pt6a ang (* flgwidth 4)))
    (setq pt7b(POLAR pt6b ang (* flgwidth 4)))
    (setq pt8 (POLAR pt2a ang1 piplen))
    (setq pt8a(POLAR pt8 ang piplen))
    (setq pt8b(POLAR pt8 (+ ang (dtr 180)) piplen))
    (setq pt9 (POLAR pt8 ang1 flglen))
    (setq pt9a(POLAR pt9 ang flglen))
    (setq pt9b(POLAR pt9 (+ ang (dtr 180)) flglen))
    (setq pt9c(POLAR pt9 ang piplen))
    (setq pt9d(POLAR pt9 (+ ang (dtr 180)) piplen))
    (setq pt2 (POLAR pt9 ang1 (* flgwidth 4)))
    (setq pt10a(POLAR pt9a ang1 (* flgwidth 4)))
    (setq pt10b(POLAR pt9b ang1 (* flgwidth 4)))
    (command "layer" "s" "2c" "")
    (command "pline" pt3a "w" "0" "0" pt3b pt4b pt4a "c")
    (command "pline" pt5a "w" "0" "0" pt5b pt7b pt7a "c")
    (command "pline" pt9a "w" "0" "0" pt9b pt10b pt10a "c")
    (command "line" pt4c pt5c "" "line" pt4d pt5d "" "line" pt6a pt6b ""
             "line" pt8a pt9c "" "line" pt8b pt9d ""
    )
    (if (= future 1)
        (if (/= dwgtype "D")(bmlist (POLAR pt1 ang1 flglen)))
    )
    (if (= sd "BW")
        (cond
            ((= future 1)
                (command "insert" "c:/ghk/iso/isoweld" pt1 sk1 "" "")
                (command "insert" "c:/ghk/iso/isoweld" pt2 sk1 "" "")
            )
            ((= future 0)
                (command "layer" "s" "2h" "")
                (command "circle" pt1 sk1)
                (command "circle" pt2 sk1)
            )
        )
    )
    (command "layer" "s" "1c" "")
    (command "line" (POLAR pt1 (+ ang (dtr 180)) (* 1.5 sk1)) (POLAR pt5 ang (* 4 sk1)) "")
    (if (= sd "BW")
        (progn
            (setq endpoint pt2)
            (command "line" (POLAR pt2a (+ ang (dtr 180)) (* 1.5 sk1)) pt2 "")
        )
        (progn
            (setq endpoint (POLAR pt2 ang (* 0.75 sk1)))
            (command "line" (POLAR pt2a (+ ang (dtr 180)) (* 1.5 sk1)) (POLAR pt2 ang (* 0.75 sk1)) "")
        )
    )
    (setq endang ang1)
    (setq con-val nil)
)

(defun i-straner()
    (if (= job_direc 1)
        (progn
            (setvar "osmode" 1)
            (SETQ pt1 (GETPOINT "\nPICK 1ST POINT OF VALVE : "))
            (IF (= pt1 nil)(setq pt1 endpoint))
            (setvar "osmode" 0)
            (setq ang (GETANGLE pt1 "\nPICK 2nd VALVE DIRECTION: "))
        )
    )
    (setvar "osmode" 0)
    (IF (= pt1 nil)(setq pt1 endpoint))
    (IF (= ang nil)(setq ang endang))
    (if (or (= sd "SW") (= sd "SCR'D") (= sd "BW"))
        (setq pt1 pt1)
        (setq pt1 (POLAR pt1 ang (* 0.75 sk1)))
    )
    (if (< ghk 49)
        (progn
            (setq flglen (* 3 sk1))
            (setq piplen (* 1.5 sk1))
            (setq flgwidth (* 1.25 (* 0.2 sk1)))
        )
        (progn
            (setq flglen (* 5 sk1))
            (setq piplen (* 2.5 sk1))
            (setq flgwidth (* 1.75 (* 0.2 sk1)))
        )
    )
    (initget 1)
    (setq ang1 (GETANGLE pt1 "\nPICK VALVE DIRECTION: "))
    (if (and (<= ang1 (+ ang (dtr 10))) (>= ang1 (- ang (dtr 10))))
        (setq ang1 (GETANGLE pt1 "\nPICK VALVE DIRECTION: "))
    )
    (if (= future 1)
        (command "layer" "s" "2c" "")
        (command "layer" "s" "2h" "")
    )
)

(defun i-straner1()
    (if (= sd "BW")
        (cond
            ((= future 1)
                (command "insert" "c:/ghk/iso/isoweld" pt1 sk1 "" "")
                (command "insert" "c:/ghk/iso/isoweld" pt2 sk1 "" "")
            )
            ((= future 0)
                (command "layer" "s" "2h" "")
                (command "circle" pt1 sk1)
                (command "circle" pt2 sk1)
            )
        )
    )
    (command "layer" "s" "1c" "")
    (if (or (= sd "SW") (= sd "SCR'D") (= sd "BW"))
        (progn
            (setq endpoint pt2)
            (command "line" pt1 pt2 "")
        )
        (progn
            (setq endpoint (POLAR pt2 ang (* 0.75 sk1)))
            (command "line" (POLAR pt1 (+ ang (dtr 180)) (* 1.5 sk1)) (POLAR pt2 ang (* 0.75 sk1)) "")
        )
    )
    (setq endang ang)
    (setq con-val nil)
)

(defun i-trap(/ flglen piplen flgwidth pt1 pt2 ang ang1 pt3 pt3a pt3b
                pt4 pt4a pt4b pt4c pt4d pt5 pta pt5b pt6 pt6a pt6b pt6c
                pt6d pt7 pt7a pt7b ang-1 ang-2 pt7c pt7d pt8 pt8a pt8b
                pt8c pt9 pt9a pt10 pt10b pt10a)
    (setiso1)
    (setq c_item "STM")
    (setq c_itemno "170")
    (sc1)
    (set-selec i-trap1)
    (setiso2)
    (setq old_sd sd)
    (if (or (= sd "SW") (= sd "SCR'D"))(val-acc1)(if (= sd "BW")(val-acc2)(val-acc)))
    (prin1)
)
(defun i-trap1()
    (if (= job_direc 2)(progn (i-gas)(i-blt)))
    (setq c_item "STM")
    (setq c_itemno "170")
    (sc1)
    (i-straner)
    (if (< ghk 49)
        (setq pt2 (POLAR pt1 ang (* 13 sk1)))
        (setq pt2 (POLAR pt1 ang (* 20 sk1)))
    )
    (setq pt3 pt1)
    (setq pt3a(POLAR pt3 (+ ang1 (dtr 180)) flglen))
    (setq pt3b(POLAR pt3 ang1 flglen))
    (setq pt4 (POLAR pt1 ang (* flgwidth 4)))
    (setq pt4a(POLAR pt4 (+ ang1 (dtr 180)) flglen))
    (setq pt4b(POLAR pt4 ang1 flglen))
    (setq pt4c(POLAR pt4 (+ ang1 (dtr 180)) piplen))
    (setq pt4d(POLAR pt4 ang1 piplen))
    (setq pt5 (POLAR pt4 ang flglen))
    (setq pt5a(POLAR pt5 (+ ang1 (dtr 180)) flglen))
    (setq pt5b(POLAR pt5 ang1 flglen))
    (setq pt5c(POLAR pt5 (+ ang1 (dtr 180)) piplen))
    (setq pt5d(POLAR pt5 ang1 piplen))
    (setq pt9 pt2)
    (setq pt9a(POLAR pt9 (+ ang1 (dtr 180)) flglen))
    (setq pt9b(POLAR pt9 ang1 flglen))
    (setq pt8 (POLAR pt9 (+ ang (dtr 180)) (* flgwidth 4)))
    (setq pt8a(POLAR pt8 (+ ang1 (dtr 180)) flglen))
    (setq pt8b(POLAR pt8 ang1 flglen))
    (setq pt8c(POLAR pt8 (+ ang1 (dtr 180)) piplen))
    (setq pt8d(POLAR pt8 ang1 piplen))
    (setq pt7 (POLAR pt8 (+ ang (dtr 180)) flglen))
    (setq pt7a(POLAR pt7 (+ ang1 (dtr 180)) flglen))
    (setq pt7b(POLAR pt7 ang1 flglen))
    (setq pt7c(POLAR pt7 (+ ang1 (dtr 180)) piplen))
    (setq pt7d(POLAR pt7 ang1 piplen))
    (setq pt6 (POLAR pt1 ang (/ (distance pt1 pt2) 2)))
    (command "pline" pt3a "w" "0" "0" pt3b pt4b pt4a "c")
    (command "pline" pt9a "w" "0" "0" pt9b pt8b pt8a "c")
    (command "pline" pt5a "w" "0" "0" pt5b pt7b pt7a "c")
    (command "line" pt4c pt5c "" "line" pt4d pt5d "" "line" pt7c pt8c ""
             "line" pt7d pt8d "")
    (setq c_itemno "1701")
    (if (= future 1)
        (if (/= dwgtype "D")(bmlist (POLAR pt1 ang1 flglen)))
    )
    (i-straner1)
)
