(defun i-tee1(/ pt1 pt2 pt0 pt3 ang ang1 pt1a pt1b pt1c pt1d
                pt2a pt2b pt2c pt2d pt3a pt3b pt3c pt3d tee-type)
    (setiso1)
    (setq c_item "TEE")
    (setq c_itemno "030")
    (setq tee-type 1)
    (i-teebase1)
    (setq tee-type nil)
    (setiso2)
    (if (or (= sd "SW") (= sd "PE") (= sd "SCR'D"))(val-acc1)(val-acc2))
    (prin1)
)

(defun i-tee2(/ pt1 pt2 pt0 pt3 ang ang1 pt1a pt1b pt1c pt1d
                pt2a pt2b pt2c pt2d pt3a pt3b pt3c pt3d tee-type)
    (setiso1)
    (setvar "osmode" 1)
    (setq c_item "TEE")
    (setq c_itemno "030")
    (setq tee-type 2)
    (i-teebase2)
    (setq tee-type nil)
    (setiso2)
    (if (or (= sd "SW") (= sd "PE") (= sd "SCR'D"))(val-acc1)(val-acc2))
    (prin1)
)

(defun i-tee3(/ pt1 pt2 pt0 pt3 ang ang1 pt1a pt1b pt1c pt1d
                pt2a pt2b pt2c pt2d pt3a pt3b pt3c pt3d tee-type)
    (setiso1)
    (setvar "osmode" 1)
    (setq c_item "RTE")
    (setq c_itemno "030")
    (setq tee-type 3)
    (ch-size ghk)
    (i-rtee)
    (if (= ok 1)(i-teebase1))
    (setq tee-type nil)
    (setiso2)
    (if (or (= sd "SW") (= sd "PE") (= sd "SCR'D"))(val-acc1)(val-acc2))
    (prin1)
)

(defun i-tee4(/ pt1 pt2 pt0 pt3 ang ang1 pt1a pt1b pt1c pt1d
                pt2a pt2b pt2c pt2d pt3a pt3b pt3c pt3d tee-type)
    (setiso1)
    (setvar "osmode" 1)
    (setq c_item "RTE")
    (setq c_itemno "030")
    (setq tee-type 4)
    (ch-size ghk)
    (i-rtee)
    (setq br-size1 ghk)
    (setq ghk br-size)
    (setq br-size br-size1)
    (if (= ok 1)(i-teebase2))
    (setq tee-type nil)
    (setiso2)
    (if (or (= sd "SW") (= sd "PE") (= sd "SCR'D"))(val-acc1)(val-acc2))
    (prin1)
)

(defun i-teebase1()
    (sc1)
    (if (= c_disc "")
        (prompt "\nIS NOT SPEC SIZE ")
        (progn
            (if (<= ghk endtype)
                (setq teelen (* 4 sk1))
                (setq teelen (* 6 sk1))
            )
            (if (= job_direc 1)
                (progn
                    (setvar "osmode" 1)
                    (SETQ pt1 (GETPOINT "\nPICK 1ST POINT OF TEE: "))
                    (setvar "osmode" 0)
                    (IF (= pt1 nil)(setq pt1 endpoint))
                    (setq ang (GETANGLE pt1 "\nPICK TEE CENTER DIRECTION: "))
                )
            )
            (setvar "osmode" 0)
            (IF (= pt1 nil)(setq pt1 endpoint))
            (IF (= ang nil)(setq ang endang))
            (setq pt0 (POLAR pt1 ang teelen))
            (initget 1)
            (setq ang1 (GETANGLE pt0 "\nPICK 2nd TEE DIRECTION: "))
            (if (and (<= ang1 (+ ang (dtr 10))) (>= ang1 (- ang (dtr 10))))
                (setq ang1 (GETANGLE pt0 "\nPICK 2nd TEE DIRECTION: "))
            )
            (setq pt3 (POLAR pt0 ang1 teelen)
                  pt2 (POLAR pt0 ang teelen)
            )
            (i-teebase)
        )
    )
)

(defun i-teebase2()
    (sc1)
    (if (= c_disc "")
        (prompt "\nIS NOT SPEC SIZE ")
        (progn
            (if (<= ghk endtype)
                (setq teelen (* 4 sk1))
                (setq teelen (* 6 sk1))
            )
            (if (= job_direc 1)
                (progn
                    (setvar "osmode" 1)
                    (SETQ pt3 (GETPOINT "\nPICK 1ST POINT OF TEE: "))
                )
            )
            (setvar "osmode" 0)
            (IF (= pt3 nil)(setq pt3 endpoint))
            (setq ang1(GETANGLE pt3 "\nPICK TEE CENTER DIRECTION: "))
            (IF (= ang1 nil)
                (setq ang1 (+ endang (dtr 180)))
                (setq ang1 (+ ang1 (dtr 180)))
            )
            (setq pt0 (POLAR pt3 (+ ang1 (dtr 180)) teelen))
            (initget 1)
            (setq ang (GETANGLE pt0 "\nPICK 2nd TEE DIRECTION: "))
            (if (and (<= ang1 (+ ang (dtr 10))) (>= ang1 (- ang (dtr 10))))
                (setq ang (GETANGLE pt0 "\nPICK 2nd TEE DIRECTION: "))
            )
            (setq pt1 (POLAR pt0 (+ ang (dtr 180)) teelen)
                  pt2 (POLAR pt0 ang teelen)
            )
            (i-teebase)
        )
    )
)

(defun i-teebase()
    (if (or (= sd "SW") (= sd "SCR'D"))
        (progn
            (setq pt1a (POLAR pt1  ang1 (* 1.5 sk1)))
            (setq pt1b (POLAR pt1a ang (* 1 sk1)))
            (setq pt1c (POLAR pt1b (+ ang1 (dtr 180)) (* 3 sk1)))
            (setq pt1d (POLAR pt1a (+ ang1 (dtr 180)) (* 3 sk1)))
            (setq pt2a (POLAR pt2  ang1 (* 1.5 sk1)))
            (setq pt2b (POLAR pt2a (+ ang (dtr 180)) (* 1 sk1)))
            (setq pt2c (POLAR pt2b (+ ang1 (dtr 180)) (* 3 sk1)))
            (setq pt2d (POLAR pt2a (+ ang1 (dtr 180)) (* 3 sk1)))
            (setq pt3a (POLAR pt3  (+ ang (dtr 180)) (* 1.5 sk1)))
            (setq pt3b (POLAR pt3a (+ ang1 (dtr 180)) (* 1 sk1)))
            (setq pt3c (POLAR pt3b ang (* 3 sk1)))
            (setq pt3d (POLAR pt3a ang (* 3 sk1)))
            (cond
                ((= future 1)
                    (setq c_itemno (strcat c_itemno "3"))
                    (if (or (= tee-type 1) (= tee-type 2))
                        (if (/= dwgtype "D") (bmlist pt0))
                        (if (/= dwgtype "D")
                            (progn
                                (if (= size-type 1)
                                    (bmlist1 pt0 (strcat (ch-size ghk) (chr 34) "x" (ch-size br-size) (chr 34)))
                                    (bmlist1 pt0 (strcat (rtos ghk 2 0) "Ax" (rtos br-size 2 0) "A"))
                                )
                            )
                        )
                    )
                    (command "layer" "s" "5c" "")
                )
                ((= future 0)
                    (command "layer" "s" "2h" "")
                )
            )
            (if (= con-type 1)
                (progn
                    (command "pline" (POLAR pt1 ang (* 1 sk1)) "w" p-wedth3 p-wedth3
                             (POLAR pt2 (+ ang (dtr 180)) (* 1 sk1)) "")
                    (command "pline" pt0 "w" p-wedth3 p-wedth3
                             (POLAR pt3 (+ ang1 (dtr 180)) (* 1 sk1)) "")
                    (command "pline" pt1a "w" p-wedth1 p-wedth1 pt1b pt1c pt1d "")
                    (command "pline" pt2a "w" p-wedth1 p-wedth1 pt2b pt2c pt2d "")
                    (command "pline" pt3a "w" p-wedth1 p-wedth1 pt3b pt3c pt3d "")
                )
                (progn
                    (command "pline" pt1 "w" p-wedth3 p-wedth3 pt2 "")
                    (command "pline" pt0 "w" p-wedth3 p-wedth3 pt3 "")
                    (command "pline" pt1a "w" p-wedth1 p-wedth1 pt1d "")
                    (command "pline" pt2a "w" p-wedth1 p-wedth1 pt2d "")
                    (command "pline" pt3a "w" p-wedth1 p-wedth1 pt3d "")
                )
            )
        )
        (progn
            (command "layer" "s" "8c" "")
            (cond
                ((= future 1)
                    (setq c_itemno (strcat c_itemno "3"))
                    (command "pline" pt1 "w" p-wedth4 p-wedth4 pt2 "")
                    (command "pline" pt0 "w" p-wedth4 p-wedth4 pt3 "")
                    (command "insert" "c:/ghk/iso/isoweld" pt1 sk1 "" "")
                    (command "insert" "c:/ghk/iso/isoweld" pt2 sk1 "" "")
                    (command "insert" "c:/ghk/iso/isoweld" pt3 sk1 "" "")
                    (if (or (= tee-type 1) (= tee-type 2))
                        (if (/= dwgtype "D") (bmlist pt0))
                        (if (/= dwgtype "D")
                            (if (= size-type 1)
                                (bmlist1 pt0 (strcat (ch-size ghk) (chr 34) "x" (ch-size br-size) (chr 34)))
                                (bmlist1 pt0 (strcat (rtos ghk 2 0) "Ax" (rtos br-size 2 0) "A"))
                            )
                        )
                    )
                )
                ((= future 0)
                    (command "layer" "s" "2h" "")
                    (command "line" pt1 pt2 "")
                    (command "line" pt0 pt3 "")
                    (command "circle" pt1 sk1)
                    (command "circle" pt2 sk1)
                    (command "circle" pt3 sk1)
                )
            )
        )
    )
    (if (or (= tee-type 3) (= tee-type 4))
        (progn
            (command "layer" "s" "2c" "")
            (if (= size-type 1)
                (command "text" "c" (POLAR pt1 ang1 (* 8 sk1)) (* txt-h s) "30" (strcat (ch-size ghk) (chr 34) "x" (ch-size br-size) (chr 34)))
                (command "text" "c" (POLAR pt1 ang1 (* 8 sk1)) (* txt-h s) "30" (strcat (rtos ghk 2 0) "Ax" (rtos br-size 2 0) "A"))
            )
            (command "text" "c" (POLAR pt1 (dtr 90) 5)  (* txt-h s) "30" "RED.TEE")
        )
    )
    (setq endpoint pt2)
    (setq endang (angle pt0 pt2))
)

(defun i-rtee(/ mainum1 s-num lst1 lst2 lst2- lst20- lst30- lst40-
                lst50- lst60- lst70- sd-1 sd-2 ghk1)
    (setq dcl_id (load_dialog "c:/ghk/iso/iredtee.dcl"))
    (if (not (new_dialog "iredtee" dcl_id))
        (exit)
    )
    (if (or (= swg-type 1) (= swg-type 3) (= tee-type 3))
        (sslist1 "i-tee")
        (if (or (= swg-type 2) (= swg-type 4) (= tee-type 4))
            (sslist1 "i-tee1")
        )
    )
    (if (not mat-code)(setq mat-code 0))
    (if (or (= swg-type 1) (= swg-type 3))
       (setq sd-1 sd)
       (setq sd-2 sd)
    )
    (if (= size-type 1)
        (setq mainsize (strcat chsize (chr 34)))
        (setq mainsize (strcat (rtos ghk 2 0) "A"))
    )
    (iset-s1)
    (setq mainum1 "0")
    (if (or (= tee-type 3) (= swg-type 1) (= swg-type 3))
        (setq s-num (- (atoi sizenum) 1))
        (setq s-num (atoi sizenum))
    )
    (setq lst2- (nth s-num lst2))
    (setq lst20- (nth 0 lst2-));brencht size
    (setq lst30- (nth 1 lst2-));ansi pipe dia
    (setq lst40- (nth 2 lst2-));jis pipe dia
    (setq lst50- (nth 3 lst2-));brencht size
    (setq lst60- (nth 4 lst2-));main pipe dia
    (setq br-size(atoi (nth 0 lst20-)))
    (if (= mat-code 0)
        (setq br-dia(nth 0 lst30-))
        (setq br-dia(nth 0 lst40-))
    )
    (if (= mat-code 0)
        (setq ma-dia(nth 0 lst60-))
        (setq ma-dia(nth 1 lst60-))
    )
    (action_tile "br_size"  "(br_1 (setq mainum1 $value))")
    (action_tile "ansicode" "(setq mat-code 0)(iset-s1)")
    (action_tile "kscode"   "(setq mat-code 1)(iset-s1)")
    (action_tile "zbr-dia"  "(setq br-dia $value)")
    (action_tile "zma-dia"  "(setq ma-dia $value)")
    (action_tile "zmainsize"  "(setq mainsize $value)")
    (start_list "br_size")
    (if (= size-type 1)
        (mapcar 'add_list lst50-)
        (mapcar 'add_list lst20-)
    )
    (end_list)
    (set_tile "br_size" "0")
    (set_tile "zbr-dia" br-dia)
    (set_tile "zma-dia" ma-dia)
    (set_tile "zmainsize" mainsize)
    (setq ok(start_dialog))
    (done_dialog)
    (unload_dialog dcl_id)
    (if (= ok 1)
        (if (or (= swg-type 1) (= swg-type 2) (= swg-type 3) (= swg-type 4))
            (progn
                (setq ghk1 ghk)
                (setq ghk br-size)
                (sc1)
                (setq ghk ghk1)
                (if (or (= swg-type 1) (= swg-type 3))
                    (setq sd-2 sd)
                    (setq sd-1 sd)
                )
                (iset-s2)
            )
        )
    )
    (princ)
)

(defun br_1(data / )
    (setq lst20- (nth 0 lst2-));brencht size
    (setq lst30- (nth 1 lst2-));ansi pipe dia
    (setq lst40- (nth 2 lst2-));jis pipe dia
    (setq lst60- (nth 4 lst2-));main pipe dia
    (setq br-size(atoi (nth (atoi data) lst20-)))
    (if (= mat-code 0)
        (setq br-dia(nth (atoi data) lst30-))
        (setq br-dia(nth (atoi data) lst40-))
    )
    (set_tile "zmainsize" mainsize)
    (set_tile "zbr-dia" br-dia)
    (set_tile "zma-dia" ma-dia)
)

(defun iset-s1()
 (if (= mat-code 1)
      (set_tile "kscode" "1")
      (set_tile "ansicode" "1")
 )
)

(defun iset-s2()
 (cond
    ((and (= sd-1 "BE")(= sd-2 "PE"))
        (setq swgend 1)
        (setq swgend1 "LBE x SPE")
    )
    ((and (= sd-1 "BE")(= sd-2 "TE"))
        (setq swgend 2)
        (setq swgend1 "LBE x STE")
    )
    ((and (= sd-1 "PE")(= sd-2 "PE"))
        (setq swgend 3)
        (setq swgend1 "PBE")
    )
    ((and (= sd-1 "TE")(= sd-2 "TE"))
        (setq swgend 4)
        (setq swgend1 "TBE")
    )
    ((and (= sd-1 "PE")(= sd-2 "TE"))
        (setq swgend 5)
        (setq swgend1 "LPE x STE")
    )
    ((and (= sd-1 "TE")(= sd-2 "PE"))
        (setq swgend 6)
        (setq swgend1 "LTE x SPE")
    )
    ((and (= sd-1 "BE")(= sd-2 "BE"))
        (setq swgend 7)
        (setq swgend1 "BBE")
    )
 )
)
