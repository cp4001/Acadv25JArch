(defun text1 () (textang 1) (princ))
(defun text2 () (textang 2) (princ))
(defun text3 () (textang 3) (princ))
(defun text4 () (textang 4) (princ))
(defun text5 () (textang 5) (princ))
(defun text6 () (textang 6) (princ))
(defun text7 () (textang 7) (princ))
(defun text8 () (textang 8) (princ))

(defun textang (num / sty obl sset ptcny pscnt acnt slist enn)
    (if (= text-type 2)
        (setq slist '((1 "T1" 30)
                     (2 "T12" 330)
                     (3 "T1" 90)
                     (4 "T1" 330)
                     (5 "T12" 30)
                     (6 "T12" 90)
                     (7 "STANDARD" 0)
                     (8 "STANDARD" 90)
                     )
                     sty (nth 1 (assoc num slist))
                     obl (nth 2 (assoc num slist))
        )
        (setq slist '((1 "STANDARD" 30)
                     (2 "STANDARD" 330)
                     (3 "STANDARD" 90)
                     (4 "STANDARD" 330)
                     (5 "STANDARD" 30)
                     (6 "STANDARD" 90)
                     (7 "STANDARD" 0)
                     (8 "STANDARD" 90)
                     )
                     sty (nth 1 (assoc num slist))
                     obl (nth 2 (assoc num slist))
        )
 ) 
 (prompt "\nPICK TEXT TO CHANGE: ")
 (setq cor_sty (getvar "textstyle"))
 (setq sset (ssget) ptcnt 0 acnt 0 pscnt (sslength sset))
 (if (not (tblsearch "style" "t1"))
     (progn
        (command "filedia" "0")
        (command "style" "t1" "romans" "" "" "30" "" "" "")
        (command "filedia" "1")
     )
 )
 (if (not (tblsearch "style" "t12"))
     (progn
        (command "filedia" "0")
        (command "style" "t12" "romans" "" "" "-30" "" "" "")
        (command "filedia" "1")
     )
 )
 (while (< ptcnt pscnt)
    (if (= "TEXT" (cdr (assoc 0 (entget (setq enn (ssname sset ptcnt))))))
        (progn
           (command "change" enn "" "" "" sty "" obl "")
           (setq ptcnt (1+ ptcnt) acnt (1+ acnt) )
        )
        (setq ptcnt (1+ ptcnt) )
    )
 )
 (setvar "textstyle" cor_sty)
 (prompt (strcat "\n"(rtos acnt 2 0) " " (if (= acnt 1) "LINE WAS" "LINES WERE")  " CHANGED."))
)

(defun i-chs(/ i sss l en el text1 d1 b1)
    (if (not (tblsearch "style" "td1"))
         (progn
            (command "filedia" "0")
            (command "style" "td1" "romand" "" "" "30" "" "" "")
            (command "filedia" "1")
         )
     )
     (if (not (tblsearch "style" "t12"))
         (progn
            (command "filedia" "0")
            (command "style" "td12" "romand" "" "" "-30" "" "" "")
            (command "filedia" "1")
         )
     )
    (setq i 0)
;    (setq sss(ssget))
;    (setq l(sslength sss))
;    (repeat l
;        (setq en(ssname sss i))
;        (setq el (entget en))
;        (setq text1 (assoc 7 el))
;        (setq d1(cons (car text1) "td1"))
;        (setq b1 (subst d1 text1 el))
;        (entmod b1)
;        (setq i(+ 1 i))
;    )
    (setq sss(ssget))
    (setq en(ssname sss i))
    (setq el (entget en))
    (setq text1 (assoc 7 el))
    (setq d1(cons (car text1) "td1"))
    (setq b1 (subst d1 text1 el))
    (entmod b1)
;    (setq en(ssname sss i))
    (setq b (entget en))
    (setq c (assoc 40 b))
    (setq c1 (assoc 0 b))
    (if (= (cdr c1) "TEXT")
     (progn
        (setq d (cons (car c) 4))
        (setq b1 (subst d c b))
        (entmod b1)
     )
    )
    (COMMAND "CHPROP" SSS "" "la" "5c" "C" "BYLAYER" "LT" "BYLAYER" "" )
)

(defun i-just(/ i sss l en el text1 d1 b1 en1 el1 text1 d1a b1a)
    (setq i 0)
    (setq ia 0)
    (setq sss(ssget))
    (setq l(sslength sss))
    (repeat l
        (setq en(ssname sss i))
        (setq el (entget en))
        (setq text1 (assoc 73 el))
        (setq d1(cons (car text1) 0))
        (setq b1 (subst d1 text1 el))
        (entmod b1)
        (setq i(+ 1 i))
    )
    (repeat l
        (setq en1(ssname sss ia))
        (setq el1 (entget en1))
        (setq text1 (assoc 72 el1))
        (setq d1a(cons (car text1) 0))
        (setq b1a (subst d1a text1 el1))
        (entmod b1a)
        (setq ia(+ 1 ia))
    )
)

(defun tj(/ sset sslen justp justq ent opt orthom loc loc1)
  (setq sset (ssget))
  (if (getvar "DIMCLRD")
    (initget (strcat "TLeft TCenter TRight "
                     "MLeft MCenter Mright "
                     "BLeft BCenter Bright "
                     "Aligned Center Fit Left Middle Right ?"))
    (initget "Aligned Center Fit Left Middle Right ?")
  )
  (setq sslen (sslength sset))
  (setq justp (getkword (strcat "\nJustification point(s) - "
              "Aligned/Center/Fit/Left/Middle/Right/<?>: ")))
  (cond
    ((= justp "Left")    (setq justp 0 justq 0) )
    ((= justp "Center")  (setq justp 1 justq 0) )
    ((= justp "Right")   (setq justp 2 justq 0) )
    ((= justp "Aligned") (setq justp 3 justq 0) )
    ((= justp "Fit")     (setq justp 5 justq 0) )
    ((= justp "TLeft")   (setq justp 0 justq 3) )
    ((= justp "TCenter") (setq justp 1 justq 3) )
    ((= justp "TRight")  (setq justp 2 justq 3) )
    ((= justp "MLeft")   (setq justp 0 justq 2) )
    ((= justp "Middle")  (setq justp 1 justq 2) )
    ((= justp "MCenter") (setq justp 1 justq 2) )
    ((= justp "MRight")  (setq justp 2 justq 2) )
    ((= justp "BLeft")   (setq justp 0 justq 1) )
    ((= justp "BCenter") (setq justp 1 justq 1) )
    ((= justp "BRight")  (setq justp 2 justq 1) )
    ((= justp "?")       (setq justp nil)       )
    (T                   (setq justp nil)       )
  )   
  (if justp
    (justpt) ; Process them...
    (justpn) ; List options...
  )
  (command)
)
;;;
;;; Get alignment points for "aligned" or "fit" text.
;;;
(defun justpt ()
  (while (> sslen 0)
    (setq ent (entget(ssname sset (setq sslen (1- sslen))))
          ent (subst (cons 72 justp) (assoc 72 ent) ent)
          opt (trans (list (cadr (assoc 10 ent))
                           (caddr (assoc 10 ent))
                           (cadddr (assoc 10 ent)))
                     (cdr(assoc -1 ent)) ; from ECS
                     1)               ; to current UCS
    )
    (if (getvar "DIMCLRD")
      (setq ent (subst (cons 73 justq) (assoc 73 ent) ent))
    )
    (cond
      ((or (= justp 3) (= justp 5))
        (prompt "\nNew text alignment points: ")
        (if (= (setq orthom (getvar "orthomode")) 1)
          (setvar "orthomode" 0)
        )
        (redraw (cdr(assoc -1 ent)) 3)
        (initget 1)
        (setq loc (getpoint))
        (initget 1)
        (setq loc1 (getpoint loc))
        (redraw (cdr(assoc -1 ent)) 1)
        (setvar "orthomode" orthom)
        (setq ent (subst (cons 10 loc) (assoc 10 ent) ent))
        (setq ent (subst (cons 11 loc1) (assoc 11 ent) ent))
      )
      ((/= justp 0)
        (redraw (cdr(assoc -1 ent)) 3)
;        (prompt "\nNew text location: ")
;        (if (= (setq orthom (getvar "orthomode")) 1)
;          (setvar "orthomode" 0)
;        )
;        (setq loc (getpoint opt))
;        (setvar "orthomode" orthom)
        (redraw (cdr(assoc -1 ent)) 1)
;        (if (null loc)
          (setq loc opt)
;          (setq loc (trans loc 1 (cdr(assoc -1 ent))))
;        )
        (setq ent (subst (cons 11 loc) (assoc 11 ent) ent))
      )
    )
    (entmod ent)
  )
)
;;;
;;; List the options.
;;;
(defun justpn ()
  (if (getvar "DIMCLRD") (textpage))
  (princ "\nAlignment options: ")
  (princ "\n\t TLeft   TCenter   TRight ")
  (princ "\n\t MLeft   MCenter   MRight ")
  (princ "\n\t BLeft   BCenter   BRight ")
  (princ "\n\t  Left    Center    Right")
  (princ "\n\tAligned   Middle    Fit")
  (if (not (getvar "DIMCLRD")) (textscr))
  (princ "\n\nPress any key to return to your drawing. ")
  (grread)
  (princ "\r                                           ")
  (graphscr)
)

(defun p-cal1(/ ia aaa n-len l a b c d e f g h i a1 b1 c1 d1 e1 f1 g1
                  h1 i1 t-len1 d-1 b-1 t-sizeno)
    (setvar "cmdecho" 0)
    (setvar "osmode" 0)
    (setq ia 0)
    (setq aaa(ssget))
    (setq l(sslength aaa))
    (repeat l
        (setq a(ssname aaa ia))
        (setq a1 (entget a))
        (if (= "GHKISO" (cdr (assoc 2 a1)))
            (progn
                (sam-1)
                (if (= "PIP" (cdr (assoc 1 d1)))
                    (progn
                        (setq t-len1(assoc 1 f1))
                        (terpri)
                        (prompt "New Length  < If Edit to Dialogue  [ D  or  Default ] =  ")
                        (princ (cdr t-len1))
                        (prompt " > : ")
                        (setq n-len(getstring " "))
                        (terpri)
                        (setq n-len(strcase n-len))
                        (setq t-sizeno (cdr (assoc 1 i1)))
                        (if (= n-len "D")
                            (progn
                                (setq n-len (cdr t-len1))
                                (ftof)
                            )
                            (if (= n-len "")
                                (setq n-len (cdr t-len1))
                            )
                        )
                        (setq d-1(cons (car t-len1) n-len))
                        (setq b-1 (subst d-1 t-len1 f1))
                        (entmod b-1)
                    )
                )
            )
        )
        (setq ia(+ 1 ia))
    )
    (command "regen")
)

(defun p-cal2(/ ia aaa n-len l a b c d e f g h i a1 b1 c1 d1 e1 f1 g1
                  h1 i1 t-len1 d-1 b-1 t-sizeno n-len1)
    (setvar "cmdecho" 0)
    (setvar "osmode" 0)
    (setq ia 0)
    (setq aaa(ssget))
    (setq n-len(getstring T "\nNew Size : "))
    (setq l(sslength aaa))
    (repeat l
        (setq a(ssname aaa ia))
        (setq a1 (entget a))
        (if (= "GHKISO" (cdr (assoc 2 a1)))
            (progn
                (sam-1)
                (setq t-len1(assoc 1 e1))
                (setq d-1(cons (car t-len1) n-len))
                (setq b-1 (subst d-1 t-len1 e1))
                (entmod b-1)
                (if (= size-type 2)
                    (progn
                        (setq r-ghk(atoi n-len))
                        (if (< (strlen (rtos r-ghk 2 0)) 3)
                            (setq n-len1(strcat "0" (rtos r-ghk 2 0)))
                            (setq n-len1(rtos r-ghk 2 0))
                        )
                    )
                    (ch-size1 (substr n-len 1 (- (strlen n-len) 1)))
                )
                (setq t-len1(assoc 1 i1))
                (setq d-1(cons (car t-len1) n-len1))
                (setq b-1 (subst d-1 t-len1 i1))
                (entmod b-1)
            )
        )
        (setq ia(+ 1 ia))
    )
    (command "regen")
)
(defun p-cal3-()
    (setq dwg_no1 (getvar "dwgname"))
    (setq dwg_no2 (getvar "dwgprefix"))
    (if (=  dwg_no2 (substr dwg_no1 1 (strlen dwg_no2)))
        (setq dwg_nno (substr dwg_no1 (+ (strlen dwg_no2) 1)))
        (setq dwg_nno dwg_no1)
    )
)
(defun p-cal3(/ ia aaa n-len l a b c d e f g h i a1 b1 c1 d1 e1 f1 g1
                  h1 i1 t-len1 d-1 b-1 t-sizeno dwg_no1 dwg_no2)
    (setvar "cmdecho" 0)
    (setvar "osmode" 0)
    (setq ia 0)
    (setq aaa(ssget "X" (list (cons 2 "GHKISO"))))
    (setq dwg_no1 (getvar "dwgname"))
    (setq dwg_no2 (getvar "dwgprefix"))
    (if (=  dwg_no2 (substr dwg_no1 1 (strlen dwg_no2)))
        (setq n-len (substr dwg_no1 (+ (strlen dwg_no2) 1)))
        (setq n-len dwg_no1)
    )
    (setq n-len (strcase n-len))
    (if(= ".DWG" (substr n-len (- (strlen n-len) 3)))
        (setq n-len (substr n-len 1 (- (strlen n-len) 4)))
    )
    (setq l(sslength aaa))
    (repeat l
        (setq a(ssname aaa ia))
        (setq a1 (entget a))
        (if (= "GHKISO" (cdr (assoc 2 a1)))
            (progn
                (sam-1)
                (setq t-len1(assoc 1 b1))
                (setq d-1(cons (car t-len1) n-len))
                (setq b-1 (subst d-1 t-len1 b1))
                (entmod b-1)
            )
        )
        (setq ia(+ 1 ia))
    )
    (command "regen")
)

(defun o_1(data)
    (setq   o_spec (nth (atoi data)   lst1))
)
(defun n_1(data)
    (setq   n_spec (nth (atoi data)   lst1))
)
(defun p-cal4(/ ia aaa l o_spec n_spec a b c d e f g h i c1 d1 e1 g1 h1
                i1 t-itemno t-sizeno bmlst1 bmlst2 bmlst1- bmlst2-
                bmlst20- bmlst21- n_spec n_disc r-spec new_ghk new_class
                c_itemno i_sock i_weld i_large endtype sd n_item r-item
                d-1 b-1)
    (setvar "cmdecho" 0)
    (setvar "osmode" 0)
    (setq ia 0)
    (setq aaa(ssget))
    (setq l(sslength aaa))
    (setq dcl_id (load_dialog "c:/ghk/iso/ssspec.dcl"))
    (if (not (new_dialog "specchange" dcl_id))
        (exit)
    )
    (sslist1 "ssspec")
    (setq   list1 "0")
;    (setq   c_class (nth 0 lst1))
    (action_tile "o_list"  "(o_1 (setq list1 $value))")
    (action_tile "n_list"  "(n_1 (setq list2 $value))")
    (start_list "o_list")
    (mapcar 'add_list lst1)
    (end_list)
    (start_list "n_list")
    (mapcar 'add_list lst1)
    (end_list)
    (setq ok(start_dialog))
    (done_dialog)
    (unload_dialog dcl_id)
    (repeat l
        (setq a(ssname aaa ia))
        (setq a1 (entget a))
        (if (= "GHKISO" (cdr (assoc 2 a1)))
            (progn
                (sam-1)
                (if (= o_spec (cdr (assoc 1 c1)))
                    (progn
                        (setq n_disc nil)
                        (setq t-itemno(substr (cdr (assoc 1 h1)) 1 3))
                        (setq t-sizeno(cdr (assoc 1 i1)))
                        (sslist2 n_spec)
                        (setq bmlst1- (nth (atoi (substr t-itemno 1 2)) bmlst1))
                        (setq i_sock (nth 0 bmlst1-))
                        (setq i_weld (nth 1 bmlst1-))
                        (setq i_large (nth 2 bmlst1-))
                        (setq bmlst2- (nth (atoi (substr t-itemno 1 2)) bmlst2))
                        (setq bmlst20- (nth 0 bmlst2-))
                        (setq bmlst21- (nth 1 bmlst2-))
                        (if (and (> (atof t-sizeno) 0) (<= (atof t-sizeno) (atof i_sock)))
                            (setq n_disc (nth 0 bmlst20-))
                            (if (and (>= (atof t-sizeno) (atof i_sock)) (<= (atof t-sizeno) (atof i_weld)))
                                (setq n_disc (nth 1 bmlst20-))
                                (if (and (>= (atof t-sizeno) (atof i_weld)) (<= (atof t-sizeno) (atof i_large)))
                                    (setq n_disc (nth 2 bmlst20-))
                                )
                            )
                        )
                        (if (and (> (atof t-sizeno) 0) (<= (atof t-sizeno) (atof i_sock)))
                            (setq sd (nth 0 bmlst21-))
                            (if (and (>= (atof t-sizeno) (atof i_sock)) (<= (atof t-sizeno) (atof i_weld)))
                                (setq sd (nth 1 bmlst21-))
                                (if (and (>= (atof t-sizeno) (atof i_weld)) (<= (atof t-sizeno) (atof i_large)))
                                    (setq sd (nth 2 bmlst21-))
                                )
                            )
                        )
                        (if (= t-itemno "060")
                            (progn
                                (cond
                                    ((= sd "WN")
                                        (setq n_item "WNF")
                                    )
                                    ((= sd "SO")
                                        (setq n_item "SOF")
                                    )
                                    ((= sd "LA")
                                        (setq n_item "LJF")
                                    )
                                    ((= sd "SW")
                                        (setq n_item "SWF")
                                    )
                                )
                                (setq r-item(assoc 1 d1))
                                (setq d-1(cons (car r-item) n_item))
                                (setq b-1 (subst d-1 r-item d1))
                                (entmod b-1)
                            )
                        )
                        (if (= n_disc nil)
                            (progn
                                (setq n_disc " ")
                                (setq n_item "NOT IS ITEM")
                                (setq r-item(assoc 1 d1))
                                (setq d-1(cons (car r-item) n_item))
                                (setq b-1 (subst d-1 r-item d1))
                                (entmod b-1)
                            )
                        )
;                        (if (/= t-itemno "080")
;                            (progn
                                (setq r-spec(assoc 1 c1))
                                (setq d-1(cons (car r-spec) n_spec))
                                (setq b-1 (subst d-1 r-spec c1))
                                (entmod b-1)
                                (setq r-disc(assoc 1 g1))
                                (setq d-1(cons (car r-disc) n_disc))
                                (setq b-1 (subst d-1 r-disc g1))
                                (entmod b-1)
;                            )
;                        )
                    )
                )
            )
        )
        (setq ia(+ 1 ia))
    )
    (command "regen")
)

(defun p-cal5(/ n-len i sel en el text n-len aaa l a b c d e f g h i a1 b1 c1 d1 e1 f1 g1
                  h1 i1 t-len1 d-1 b-1 t-sizeno q_con jhg)
    (command "cmdecho" "0")
    (setq n-len 0)
    (setq i 0)
    (setq sel(ssget))
    (setq l(sslength sel))
    (repeat l
        (setq en(ssname sel i))
        (setq el (entget en))
        (if (= "TEXT" (cdr (assoc 0 el)))
            (progn
                (setq text (cdr (assoc 1 el)))
                (setq n-len(+ n-len (atof text)))
                (setq i(+ 1 i))
            )
        )
    )
    (setq n-len(rtos n-len 2 1))
    (prompt "\n Select Info Block  ")
    (setq aaa(ssget))
    (setq l(sslength aaa))
    (setq a(ssname aaa 0))
    (setq a1 (entget a))
    (if (= "GHKISO" (cdr (assoc 2 a1)))
        (progn
            (sam-1)
            (if (= "PIP" (cdr (assoc 1 d1)))
                (setq t-len1(assoc 1 f1))
            )
            (setq t-sizeno (cdr (assoc 1 i1)))
            (if (< 99 (atof t-sizeno))
                (progn
                    (if (not ftof)(load"c:/ghk/iso/iso-base"))
                    (ftof)
                )
            )
            (setq d-1 (cons (car t-len1) n-len))
            (setq b-1 (subst d-1 t-len1 f1))
            (entmod b-1)
        )
    )
    (setq q_con (strcase (getstring "\nDo you want to continue < Yes / No > { Default = Y }: ")))
    (if (= q_con "N")(setq jhg nil)(setq jhg 7))
    (while jhg
        (setq n-len 0)
        (setq i 0)
        (setq sel(ssget))
        (if (= sel nil)
            (setq jhg nil)
            (progn
                (setq l(sslength sel))
                (repeat l
                    (setq en(ssname sel i))
                    (setq el (entget en))
                    (if (= "TEXT" (cdr (assoc 0 el)))
                        (progn
                            (setq text (cdr (assoc 1 el)))
                            (setq n-len(+ n-len (atof text)))
                            (setq i(+ 1 i))
                        )
                    )
                )
                (setq n-len(rtos n-len 2 1))
                (prompt "\n Select Info Block  ")
                (setq aaa(ssget))
                (setq l(sslength aaa))
                (setq a(ssname aaa 0))
                (setq a1 (entget a))
                (if (= "GHKISO" (cdr (assoc 2 a1)))
                    (progn
                        (sam-1)
                        (if (= "PIP" (cdr (assoc 1 d1)))
                            (setq t-len1(assoc 1 f1))
                        )
                        (setq t-sizeno (cdr (assoc 1 i1)))
                        (if (< 99 (atof t-sizeno))
                            (progn
                                (ftof)
                            )
                        )
                        (setq d-1 (cons (car t-len1) n-len))
                        (setq b-1 (subst d-1 t-len1 f1))
                        (entmod b-1)
                    )
                )
            )
        )
    )
    (command "regen")
)

(defun p-cal6(/ n-len i sel en el text n-len aaa l a b c d e f g h i a1 b1 c1 d1 e1 f1 g1
                  h1 i1 t-len1 d-1 b-1 t-sizeno q_con jhg)
    (command "cmdecho" "0")
    (setq n-len 0)
    (setq i 0)
    (setq sel(ssget))
    (setq l(sslength sel))
    (repeat l
        (setq en(ssname sel i))
        (setq el (entget en))
        (if (= "TEXT" (cdr (assoc 0 el)))
            (progn
                (setq text (cdr (assoc 1 el)))
                (setq n-len(+ n-len (atof text)))
                (setq i(+ 1 i))
            )
        )
    )
    (setq n-len(rtos (* n-len 1000) 2 1))
    (prompt "\n Select Info Block  ")
    (setq aaa(ssget))
    (setq l(sslength aaa))
    (setq a(ssname aaa 0))
    (setq a1 (entget a))
    (if (= "GHKISO" (cdr (assoc 2 a1)))
        (progn
            (sam-1)
            (if (= "PIP" (cdr (assoc 1 d1)))
                (setq t-len1(assoc 1 f1))
            )
            (setq t-sizeno (cdr (assoc 1 i1)))
            (if (< 99 (atof t-sizeno))
                (progn
                    (if (not ftof)(load"c:/ghk/iso/iso-base"))
                    (ftof)
                )
            )
            (setq d-1 (cons (car t-len1) n-len))
            (setq b-1 (subst d-1 t-len1 f1))
            (entmod b-1)
        )
    )
    (setq q_con (strcase (getstring "\nDo you want to continue < Yes / No > { Default = Y }: ")))
    (if (= q_con "N")(setq jhg nil)(setq jhg 7))
    (while jhg
        (setq n-len 0)
        (setq i 0)
        (setq sel(ssget))
        (if (= sel nil)
            (setq jhg nil)
            (progn
                (setq l(sslength sel))
                (repeat l
                    (setq en(ssname sel i))
                    (setq el (entget en))
                    (if (= "TEXT" (cdr (assoc 0 el)))
                        (progn
                            (setq text (cdr (assoc 1 el)))
                            (setq n-len(+ n-len (atof text)))
                            (setq i(+ 1 i))
                        )
                    )
                )
                (setq n-len(rtos (* n-len 1000) 2 1))
                (prompt "\n Select Info Block  ")
                (setq aaa(ssget))
                (setq l(sslength aaa))
                (setq a(ssname aaa 0))
                (setq a1 (entget a))
                (if (= "GHKISO" (cdr (assoc 2 a1)))
                    (progn
                        (sam-1)
                        (if (= "PIP" (cdr (assoc 1 d1)))
                            (setq t-len1(assoc 1 f1))
                        )
                        (setq t-sizeno (cdr (assoc 1 i1)))
                        (if (< 99 (atof t-sizeno))
                            (progn
                                (ftof)
                            )
                        )
                        (setq d-1 (cons (car t-len1) n-len))
                        (setq b-1 (subst d-1 t-len1 f1))
                        (entmod b-1)
                    )
                )
            )
        )
    )
    (command "regen")
)

(defun lineno(/ dcl_id f-no s-no b-spec b-ghk b-el ok)
    (setq dcl_id (load_dialog "c:/ghk/iso/valist.dcl"))
    (if (not old_point)(setq old_point '(640 480)))
    (if (not (new_dialog "lineno" dcl_id "" old_point))
        (exit)
    )
    (setq f-no "0-63200-")
    (setq s-no c_dwgname)
    (setq b-spec c_class)
    (setq b-ghk (rtos ghk 2 0))
    (setq b-el "2500")
    (if (not el-type)(setq el-type 1))
    (cond ((= 1 el-type) (set_tile "zeltype1" "1"))
          ((= 0 el-type) (set_tile "zeltype2" "1"))
    )
    (action_tile "accept" "(progn (setq x $x y $y) (setq old_point (done_dialog 1)))")
    (action_tile "zfno"    "(setq f-no $value)")
    (action_tile "zsno"    "(setq s-no $value)")
    (action_tile "zspec"   "(setq b-spec $value)")
    (action_tile "zghk"    "(setq b-ghk $value)")
    (action_tile "zel"     "(setq b-el $value)")
    (action_tile "zeltype1" "(setq el-type 1)")
    (action_tile "zeltype2" "(setq el-type 0)")
    (mode_tile "zsno" 2)
    (set_tile "zfno" f-no)
    (set_tile "zsno" s-no)
    (set_tile "zspec" b-spec)
    (set_tile "zghk" b-ghk)
    (set_tile "zel" b-el)
    (setq ok(start_dialog))
    (done_dialog)
    (unload_dialog dcl_id)
    (if (= ok 1)(line_act))
    (princ)
)


(defun line_act(/ pt1 pt2 ang cor_sty li-no li-el textlen pt3 pt4 pt5
                  pt6 pt7 pt8)
    (setiso1)
    (setvar "osmode" 33)
    (SETQ pt1 (GETPOINT     "\nSTART POINT  : "))
    (setvar "osmode" 0)
    (setq pt2 (GETPOINT pt1 "\nSECOND POINT : "))
    (setq ang (angle pt1 pt2))
    (setq cor_sty (getvar "textstyle"))
    (setvar "textstyle" "standard")
    (setq li-no (strcat f-no s-no "-" b-spec "-" b-ghk))
    (cond ((= 1 el-type) (setq li-el (strcat "BOP EL." b-el)))
          ((= 0 el-type) (setq li-el (strcat "EL." b-el)))
    )
    (setq textlen(* (strlen li-no) s 2))
    (setq pt3 (POLAR pt1 ang (* 2 s)))
    (setq pt4 (POLAR pt3 (+ ang (dtr 90)) (* 0.5 s)))
    (setq pt5 (POLAR pt3 (+ ang (dtr 270)) (* 4 s)))
    (setq pt6 (POLAR pt1 ang textlen))
    (setq pt7 (POLAR pt6 (+ ang (dtr 90)) (* 1.5 s)))
    (setq pt8 (POLAR pt6 (+ ang (dtr 270)) (* 3 s)))
    (command "layer" "s" "2c" "")
    (line_act1)
    (command "line" pt3 pt6 "")
    (setvar "textstyle" cor_sty)
    (setiso2)
)




(defun line_act1()
    (if (= text-type 2)
        (progn
            (if (not (tblsearch "style" "t1"))
                (progn
                    (command "filedia" "0")
                    (command "style" "t1" "romans" "" "" "30" "" "" "")
                    (command "filedia" "1")
                )
            )
            (if (not (tblsearch "style" "t12"))
                (progn
                    (command "filedia" "0")
                    (command "style" "t12" "romans" "" "" "-30" "" "" "")
                    (command "filedia" "1")
                )
           )
        )
    )
    (cond
        ((and (>= (rtd ang) 15) (<= (rtd ang) 60))
            (if (= text-type 2)
                (setvar "textstyle" "t1")
                (setvar "textstyle" "standard")
            )
            (command "text" "bl" pt4 (* txt-h s) (rtd ang) li-no)
            (command "text" "bl" pt5 (* txt-h s) (rtd ang) li-el)
        )
        ((and (>= (rtd ang) 61) (<= (rtd ang) 120))
            (if (= text-type 2)
                (setvar "textstyle" "t12")
                (setvar "textstyle" "standard")
            )
            (command "text" "bl" pt4 (* txt-h s) (rtd ang) li-no)
            (command "text" "bl" pt5 (* txt-h s) (rtd ang) li-el)
         )
        ((and (>= (rtd ang) 121) (<= (rtd ang) 180))
            (if (= text-type 2)
                (setvar "textstyle" "t1")
                (setvar "textstyle" "standard")
            )
            (command "text" "tl" pt8 (* txt-h s) (+ (rtd ang) 180) li-no)
            (command "text" "tl" pt7 (* txt-h s) (+ (rtd ang) 180) li-el)
        )
        ((and (>= (rtd ang) 181) (<= (rtd ang) 240))
            (if (= text-type 2)
                (setvar "textstyle" "t1")
                (setvar "textstyle" "standard")
            )
            (command "text" "tl" pt8 (* txt-h s) (+ (rtd ang) 180) li-no)
            (command "text" "tl" pt7 (* txt-h s) (+ (rtd ang) 180) li-el)
        )
        ((and (>= (rtd ang) 241) (<= (rtd ang) 300))
            (if (= text-type 2)
                (setvar "textstyle" "t12")
                (setvar "textstyle" "standard")
            )
            (command "text" "tl" pt8 (* txt-h s) (+ (rtd ang) 180) li-no)
            (command "text" "tl" pt7 (* txt-h s) (+ (rtd ang) 180) li-el)
        )
        ((and (>= (rtd ang) 301) (<= (rtd ang) 360))
            (if (= text-type 2)
                (setvar "textstyle" "t12")
                (setvar "textstyle" "standard")
            )
            (command "text" "bl" pt4 (* txt-h s) (rtd ang) li-no)
            (command "text" "bl" pt5 (* txt-h s) (rtd ang) li-el)
        )
    )
)
