;;;;;;Front 90elbow turn lisp
(defun i-90elbow(/ pt0 pt2)
    (setiso1)
    (setq c_item "90E")
    (setq c_itemno "010")
    (sc1)
    (if (= c_disc "")
        (prompt "\nIS NOT SPEC SIZE ")
        (i-elbow1)
    )
    (setiso2)
    (if (or (= sd "SW") (= sd "PE") (= sd "SCR'D"))(val-acc1)(val-acc2))
    (prin1)
)
(defun i-45elbow(/ pt0 pt2)
    (setiso1)
    (setq c_item "45E")
    (setq c_itemno "010")
    (if (not sc1)(load"c:/ghk/iso/iso-base"))
    (sc1)
    (if (= c_disc "")
        (prompt "\nIS NOT SPEC SIZE ")
        (i-elbow1)
    )
    (setiso2)
    (if (or (= sd "SW") (= sd "PE") (= sd "SCR'D"))(val-acc1)(val-acc2))
    (prin1)
)

(defun i-elbowbase1(e_tag / elbowlen pt1 ang pt0 ang1 pt2 pt3 pt4 pt5 pt6 pt7
                            pt8 pt9 pt10)
    (setq elbowlen e_tag)
    (setvar "osmode" 1)
    (if (= job_direc 1)
        (progn
            (SETQ pt1 (GETPOINT "\nPICK 1ST POINT OF ELBOW: "))
            (setvar "osmode" 0)
            (IF (= pt1 nil)(setq pt1 endpoint))
            (setq ang (GETANGLE pt1 "\nPICK ELBOW CENTER DIRECTION: "))
        )
    )
    (IF (= pt1 nil)(setq pt1 endpoint))
    (IF (= ang nil)(setq ang endang))
    (setq pt0 (POLAR pt1 ang elbowlen))
    (initget 1)
    (setq ang1 (GETANGLE pt0 "\nPICK 2nd ELBOW DIRECTION: "))
    (setq pt2 (POLAR pt0 ang1 elbowlen))
    (i-elbow)
)

(defun i-elbowbase2(e_tag / elbowlen pt1 ang pt0 ang1 pt2 pt3 pt4 pt5 pt6 pt7
                            pt8 pt9 pt10)
    (setq elbowlen e_tag)
    (setvar "osmode" 33)
    (SETQ pt0 (GETPOINT "\nPICK POINT OF ELBOW CENTER : "))
    (setvar "osmode" 0)
    (initget 1)
    (setq ang (GETANGLE pt0 "\nPICK 1st ELBOW DIRECTION: "))
    (setq ang (+ ang (dtr 180)))
    (setq pt1 (POLAR pt0 (+ ang (dtr 180)) elbowlen))
    (setq ang1(GETANGLE pt0 "\nPICK 2nd ELBOW DIRECTION: "))
    (setq pt2 (POLAR pt0 ang1 elbowlen))
    (i-elbow)
)

(defun i-elbow()
    (setvar "osmode" 0)
;    (if (<= ghk endtype)
    (if (or (= sd "SW") (= sd "SCR'D"))
        (progn
            (setq pt3 (POLAR pt1 (+ ang1 (dtr 180)) (* 1.5 sk1)))
            (setq pt4 (POLAR pt3 ang (* 1 sk1)))
            (setq pt5 (POLAR pt4 ang1 (* 3 sk1)))
            (setq pt6 (POLAR pt3 ang1 (* 3 sk1)))
            (setq pt7 (POLAR pt2 (+ ang (dtr 180)) (* 1.5 sk1)))
            (setq pt8 (POLAR pt7 (+ ang1 (dtr 180)) (* 1 sk1)))
            (setq pt9 (POLAR pt8 ang (* 3 sk1)))
            (setq pt10(POLAR pt7 ang (* 3 sk1)))
            (cond
                ((= future 1)
                    (if (= c_item "90E")
                        (setq c_itemno (strcat c_itemno "1"))
                        (setq c_itemno (strcat c_itemno "2"))
                    )
                    (if (/= dwgtype "D")
                        (progn
                            (bmlist pt0)
                            (command "layer" "s" "5C" "")
                            (command "line" pt1 pt0 pt2 "")
                        )
                    )
                )
                ((= future 0)
                    (command "layer" "s" "2h" "")
                )
            )
            (if (= con-type 1)
                (progn
                    (command "pline" (POLAR pt1 ang (* 1 sk1)) "w" p-wedth3 p-wedth3 pt0
                        (POLAR pt2 (+ ang1 (dtr 180)) (* 1 sk1)) "")
                    (command "pline" pt3 "w" p-wedth1 p-wedth1 pt4 pt5 pt6 "")
                    (command "pline" pt7 "w" p-wedth1 p-wedth1 pt8 pt9 pt10 "")
                )
                (progn
                    (command "pline" pt1 "w" p-wedth3 p-wedth3 pt0 pt2 "")
                    (command "pline" pt3 "w" p-wedth1 p-wedth1 pt6 "")
                    (command "pline" pt7 "w" p-wedth1 p-wedth1 pt10 "")
                )
            )
        )
        (progn
            (command "layer" "s" "8c" "")
            (cond
                ((= future 1)
                    (command "pline" pt1 "w" p-wedth4 p-wedth4 pt0 pt2 "")
                    (command "insert" "c:/ghk/iso/isoweld" pt1 sk1 "" "")
                    (command "insert" "c:/ghk/iso/isoweld" pt2 sk1 "" "")
                    (if (= c_item "90E")
                        (setq c_itemno (strcat c_itemno "1"))
                        (setq c_itemno (strcat c_itemno "2"))
                    )
                    (if (/= dwgtype "D")
                        (progn
                            (bmlist pt0)
                            (command "layer" "s" "1C" "")
                            (command "line" pt1 pt0 pt2 "")
                        )
                    )
                )
                ((= future 0)
                    (command "layer" "s" "2h" "")
                    (command "line" pt1 pt0 pt2 "")
                    (command "circle" pt1 sk1)
                    (command "circle" pt2 sk1)
                )
            )
        )
    )
    (setq endpoint pt2)
    (setq endang (angle pt0 pt2))
)

(defun i-elbow1()
    (if (= v-point 1)
        (if (<= ghk endtype)
            (i-elbowbase1 (* 5 sk1))
            (i-elbowbase1 (* 8 sk1))
        )
        (if (<= ghk endtype)
            (i-elbowbase2 (* 5 sk1))
            (i-elbowbase2 (* 8 sk1))
        )
    )
)
