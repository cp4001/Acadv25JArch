;;;;;;Front 90elbow turn lisp
(defun i-pipe(/ pt1 pt2 n-len)
    (setiso1)
    (setvar "osmode" 1)
    (setq c_item "PIP")
    (setq c_itemno "000")
    (sc1)
    (set-selec i-pipe1)
    (setiso2)
    (if (or (= sd "SW") (= sd "PE") (= sd "TE") (= sd "SCR'D"))(val-acc3)(val-acc2))
    (prin1)
)
(defun i-pipe1()
    (if (= job_direc 1)
        (SETQ pt1 (GETPOINT "\nPICK START POINT OF PIPE : "))
    )
    (setvar "osmode" 0)
    (IF (= pt1 nil)(setq pt1 endpoint))
    (setq pt2 (GETPOINT pt1 "\nPICK END POINT OF PIPE : "))
    (IF (= endang nil) (setq endang (rtd 30)))
    (IF (= pt2 nil) (setq pt2 (POLAR pt1 endang (* 10 sk1))))
    (if (not n-len)(setq n-len "1000"))
    (setq ang (angle pt1 pt2))
    (cond
        ((= future 1)
;            (if (<= ghk endtype)
            (if (or (= sd "TE") (= sd "PE"))
                (progn
                    (command "layer" "s" "5c" "")
                    (command "pline" pt1 "w" (if (= future 0) "0" p-wedth3) (if (= future 0) "0" p-wedth3) pt2 "")
                    (if (/= dwgtype "D")(bmlist3 (polar pt1 ang (/ (distance pt1 pt2) 2)) n-len))
                )
                (progn
                    (command "layer" "s" "8c" "")
                    (command "pline" pt1 "w" p-wedth4 p-wedth4 pt2 "")
                    (if (/= dwgtype "D")(bmlist3 (polar pt1 ang (/ (distance pt1 pt2) 2)) n-len))
                )
            )
        )
        ((= future 0)
            (command "layer" "s" "2h" "")
            (command "line" pt1 pt2 "")
        )
    )
    (setq endpoint pt2)
    (setq endang (angle pt1 pt2))
)
