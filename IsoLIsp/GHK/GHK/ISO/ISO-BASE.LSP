;Set iso no.1
(defun setiso1()
    (setq olderr *error* *error* ghkerr)
    (setvar "cmdecho" 0)
    (layer1)
    (graphscr)
    (if (= ghk nil)(setq ghk 150))
    (command "layer" "t" "*" "")
    (setq la (getvar "clayer"))
    (setq orth(getvar "orthomode"))
    (setq os(getvar "osmode"))
    (setq c_dwgname(getvar "dwgname"))
    (if (= (strcase (substr c_dwgname (- (strlen c_dwgname) 3))) ".DWG")
        (setq c_dwgname(substr c_dwgname 1 (- (strlen c_dwgname) 4)))
    )
    (if (> (strlen (getvar "dwgprefix")) (strlen (getvar "dwgname")))
        (setq c_dwgname c_dwgname
          file_no (strcat (getvar "dwgprefix") c_dwgname)
        )
        (setq c_dwgname(substr (getvar "dwgname") (+ (strlen (getvar "dwgprefix")) 1))
	      file_no (getvar "dwgprefix")
        )
    )
    (if (= c_dwgname "")
        (setq c_dwgname "UNNAME")
    )
    (if (or (= c_class "None") (= c_class " "))
        (progn
            (ssspec)
            (resetiso)
        )
    )
)

(defun setiso2()
    (setq olderr *error* *error* ghkerr)
    (setvar "orthomode" orth)
    (setvar "osmode" os)
    (command "layer" "s" la "")
    (setq sd1 nil)
    (resetiso)
)

(defun set-selec(selec1 /)
    (if (and (= c_disc "") (= con-val nil))
        (prompt "\nIS NOT SPEC SIZE ")
        (selec1)
    )
)

(defun sam-1()
  (setq b(entnext a))
  (setq c(entnext b))
  (setq d(entnext c))
  (setq e(entnext d))
  (setq f(entnext e))
  (setq g(entnext f))
  (setq h(entnext g))
  (setq i(entnext h))
  (setq a1 (entget a))
  (setq b1 (entget b));;DWGNAME
  (setq c1 (entget c));;CLASS
  (setq d1 (entget d));;ITEM
  (setq e1 (entget e));;SIZE
  (setq f1 (entget f));;LENGTH
  (setq g1 (entget g));;DISCRIPTION
  (setq h1 (entget h));;ITEM NO
  (setq i1 (entget i));;SIZE NO
)

(defun C:DM()
       (IF (not DIMEN)(load"c:/ghk/iso/DIMEN"))
       (setvar "cmdecho" 0)
       (princ " = ISO Demension")
       (DIMEN)
)

(defun C:bm()
       (IF (not bm)(load"c:/ghk/iso/bm"))
       (bm)
)

(defun C:C1()
       (command "layer" "off" "ghkiso" "")
)
(defun c:c2()
       (command "layer" "on" "ghkiso" "")
)

(defun C:DM1()
       (IF (not DIMEN1)(load"c:/ghk/iso/DIMEN"))
       (setvar "cmdecho" 0)
       (princ " = ISO Demension")
       (DIMEN1)
)

(defun C:P1()
       (IF (not P-CAL1)(load"c:/ghk/iso/textang"))
       (setvar "cmdecho" 0)
       (princ " = PIPE Calcu.")
       (c:p-cal1)
)

(defun C:P2()
       (IF (not P-CAL2)(load"c:/ghk/iso/textang"))
       (setvar "cmdecho" 0)
       (princ " = PIPE SIZE Calcu.")
       (c:p-cal2)
)

(defun C:P3()
       (IF (not P-CAL3)(load"c:/ghk/iso/textang"))
       (setvar "cmdecho" 0)
       (princ " = DWG. NO Calcu.")
       (c:p-cal3)
)

(defun C:P4()
       (IF (not P-CAL4)(load"c:/ghk/iso/textang"))
       (setvar "cmdecho" 0)
       (princ " = SPEC CHANGE ")
       (c:p-cal4)
)

(defun C:P5()
       (IF (not P-CAL5)(load"c:/ghk/iso/textang"))
       (setvar "cmdecho" 0)
       (princ " = New Length ")
       (c:p-cal5)
)

(defun C:P6()
       (IF (not P-CAL6)(load"c:/ghk/iso/textang"))
       (setvar "cmdecho" 0)
       (princ " = New Length ")
       (c:p-cal6)
)

(defun C:TJ()
       (IF (not TJ)(load"c:/ghk/iso/textang"))
       (setvar "cmdecho" 0)
       (princ " = TEXT JUSTFICATION ")
       (TJ)
)
(defun resetiso()
    (setvar "modemacro" (strcat "Layer:$(substr,$(getvar,clayer),1,8)"
                            " Spec : " (strcat "[" c_class "] ")
                            (if (= ghk nil) " Unselect Size" (strcat " " (rtos ghk 2 0) "A "))
                            " Rat:"(if (= rat "A") " 150#" (if (= rat "B") " 300#" (if (= rat "C") " 600#" (if (= rat "D") " 900#" (if (= rat "E") " 1500#")))))
                            " Flg:"(if (= sd "SO") " SLIP ON" (if (= sd "LA") " LAP JOINT" (if (= sd "WN") " WELD NECK" (if (= sd "SW") " SOCK WELD" (if (= sd "SCR'D") " SCR'D" sd)))))
                            "  " (if (= future 1) " CONT. " (if (= future 0) " HIDDEN "))
                        )
    )
    (isobase1)
)

;Data file read
(defun sslist1 (file / fn n-line if1)
 (setq lst1 nil lst2 nil)
 (setq fn(open (strcat "c:/ghk/iso/" file".dat") "r"))
 (setq msg(read-line fn))
 (while (setq n-line(read-line fn))
        (setq if1(substr n-line 1 1))
        (cond ((= if1 "*")
               (setq lst1(cons (substr n-line 2) lst1))
              )
              ((= if1 "(")
               (setq lst2(cons (read n-line) lst2))
              )
        )
 )
 (setq lst1(reverse lst1) lst2(reverse lst2))
 (close fn)
)

;Data file read
(defun sslist2 (file / fn n-line if1)
 (setq bmlst1 nil bmlst2 nil)
 (setq fn(open (strcat "c:/ghk/iso/" file".spc") "r"))
 (setq msg(read-line fn))
 (while (setq n-line(read-line fn))
        (setq if1(substr n-line 1 1))
        (cond ((= if1 "*")
               (setq bmlst1(cons (read (substr n-line 2)) bmlst1))
              )
              ((= if1 "(")
               (setq bmlst2(cons (read n-line) bmlst2))
              )
        )
 )
 (setq bmlst1(reverse bmlst1) bmlst2(reverse bmlst2))
)

(defun isobase(/ aaa a b c d e f g h a1 b1 c1 d1 e1 f1 g1 h1)
    (setvar "cmdecho" 0)
    (setvar "attdia" 0)
    (setq aaa(ssget "X" (list (cons 0 "INSERT")(cons 2 "ISOBASE"))))
    (if (/= aaa nil)
        (progn
            (setq a(ssname aaa 0))
            (setq b(entnext a))
            (setq c(entnext b))
            (setq d(entnext c))
            (setq e(entnext d))
            (setq f(entnext e))
            (setq g(entnext f))
            (setq h(entnext g))
            (setq i(entnext h))
            (setq a1 (entget a))
            (setq b1 (entget b));;DWGNAME
            (setq c1 (entget c));;CLASS
            (setq d1 (entget d));;RATING
            (setq e1 (entget e));;SIZE
            (setq f1 (entget f));;END TYPE
            (setq g1 (entget g));;CONNECTION TYPE
            (setq h1 (entget h));;HAND WHILE
            (setq i1 (entget i));;SIZE TYPE
            (setq c_class   (cdr (assoc 1 c1)))
            (setq rat       (cdr (assoc 1 d1)))
            (setq ghk       (atoi (cdr (assoc 1 e1))))
            (setq sd        (cdr (assoc 1 f1)))
            (setq con-type  (atoi (cdr (assoc 1 g1))))
            (setq hand-type (atoi (cdr (assoc 1 h1))))
            (setq size-type (atoi (cdr (assoc 1 i1))))
            (resetiso)
        )
    )
)

(defun isobase1(/ aaa a b c d e f g h a1 b1 c1 d1 e1 f1 g1 h1 ghk1
                  con-type1 hand-type1 r-dwgname d-1 b-1 r-spec r-ghk
                  r-rat r-sd r-con-type r-hand-type r-size-type)
    (setvar "cmdecho" 0)
    (setvar "attdia" 0)
    (setq aaa(ssget "X" (list (cons 0 "INSERT")(cons 2 "ISOBASE"))))
    (setq a(ssname aaa 0))
    (setq b(entnext a))
    (setq c(entnext b))
    (setq d(entnext c))
    (setq e(entnext d))
    (setq f(entnext e))
    (setq g(entnext f))
    (setq h(entnext g))
    (setq i(entnext h))
    (setq a1 (entget a))
    (setq b1 (entget b));;DWGNAME
    (setq c1 (entget c));;CLASS
    (setq d1 (entget d));;RATING
    (setq e1 (entget e));;SIZE
    (setq f1 (entget f));;END TYPE
    (setq g1 (entget g));;CONNECTION TYPE
    (setq h1 (entget h));;HAND WHILE
    (setq i1 (entget i));;SIZE TYPE
    (setq c_dwgname(getvar "dwgname"))
    (if (= (strcase (substr c_dwgname (- (strlen c_dwgname) 3))) ".DWG")
        (setq c_dwgname(substr c_dwgname 1 (- (strlen c_dwgname) 4)))
    )
    (if (> (strlen (getvar "dwgprefix")) (strlen (getvar "dwgname")))
        (setq c_dwgname c_dwgname
          file_no (strcat (getvar "dwgprefix") c_dwgname)
        )
        (setq c_dwgname(substr (getvar "dwgname") (+ (strlen (getvar "dwgprefix")) 1))
	      file_no (getvar "dwgprefix")
        )
    )
    (setq ghk1 (rtos ghk 2 0))
    (setq con-type1  (rtos con-type 2 0))
    (setq hand-type1 (rtos hand-type 2 0))
    (setq size-type1 (rtos size-type 2 0))
    (setq r-dwgname(assoc 1 b1))
    (setq d-1(cons (car r-dwgname) c_dwgname))
    (setq b-1 (subst d-1 r-dwgname b1))
    (entmod b-1)
    (setq r-spec(assoc 1 c1))
    (setq d-1(cons (car r-spec) c_class))
    (setq b-1 (subst d-1 r-spec c1))
    (entmod b-1)
    (setq r-rat(assoc 1 d1))
    (setq d-1(cons (car r-rat) rat))
    (setq b-1 (subst d-1 r-rat d1))
    (entmod b-1)
    (setq r-ghk(assoc 1 e1))
    (setq d-1(cons (car r-ghk) ghk1))
    (setq b-1 (subst d-1 r-ghk e1))
    (entmod b-1)
    (setq r-sd(assoc 1 f1))
    (setq d-1(cons (car r-sd) sd))
    (setq b-1 (subst d-1 r-sd f1))
    (entmod b-1)
    (setq r-con-type(assoc 1 g1))
    (setq d-1(cons (car r-con-type) con-type1))
    (setq b-1 (subst d-1 r-con-type g1))
    (entmod b-1)
    (setq r-hand-type(assoc 1 h1))
    (setq d-1(cons (car r-hand-type) hand-type1))
    (setq b-1 (subst d-1 r-hand-type h1))
    (entmod b-1)
    (setq r-size-type(assoc 1 i1))
    (setq d-1(cons (car r-size-type) size-type1))
    (setq b-1 (subst d-1 r-size-type i1))
    (entmod b-1)
    (setvar "attdia" 1)
)

(defun bmlist(i_pnt / r-ghk)
 (setvar "cmdecho" 0)
 (setvar "attdia" 0)
 (if (< (strlen (rtos ghk 2 0)) 3)
    (setq r-ghk(strcat "0" (rtos ghk 2 0)))
    (setq r-ghk(rtos ghk 2 0))
 )
 (command "layer" "s" "ghkiso" "")
 (if (= size-type 1)
     (command "insert" "c:/ghk/iso/ghkiso" i_pnt  "" "" "" c_dwgname
         c_class c_item (strcat (ch-size ghk) (chr 34))  "" c_disc c_itemno r-ghk
     )
     (command "insert" "c:/ghk/iso/ghkiso" i_pnt  "" "" "" c_dwgname
         c_class c_item (strcat (rtos ghk 2 0) "A")  "" c_disc c_itemno r-ghk
     )
 )
)

(defun bmlist1(i_pnt i_size / r-ghk)
 (setvar "cmdecho" 0)
 (setvar "attdia" 0)
 (if (< (strlen (rtos ghk 2 0)) 3)
    (setq r-ghk(strcat "0" (rtos ghk 2 0)))
    (setq r-ghk(rtos ghk 2 0))
 )
 (command "layer" "s" "ghkiso" "")
 (command "insert" "c:/ghk/iso/ghkiso" i_pnt  "" "" "" c_dwgname
     c_class c_item i_size  "" c_disc c_itemno r-ghk
 )
)

(defun bmlist2(i_pnt i_size i_qty / r-ghk)
 (setvar "cmdecho" 0)
 (setvar "attdia" 0)
 (if (< (strlen (rtos ghk 2 0)) 3)
    (setq r-ghk(strcat "0" (rtos ghk 2 0)))
    (setq r-ghk(rtos ghk 2 0))
 )
 (command "layer" "s" "ghkiso" "")
 (command "insert" "c:/ghk/iso/ghkiso" i_pnt  "" "" "" c_dwgname
                            c_class c_item i_size i_qty c_disc c_itemno r-ghk)
)

(defun bmlist3(i_pnt i_qty / r-ghk)
 (setvar "cmdecho" 0)
 (setvar "attdia" 0)
 (if (< (strlen (rtos ghk 2 0)) 3)
    (setq r-ghk(strcat "0" (rtos ghk 2 0)))
    (setq r-ghk(rtos ghk 2 0))
 )
 (command "layer" "s" "ghkiso" "")
 (if (= size-type 1)
     (command "insert" "c:/ghk/iso/ghkiso" i_pnt  "" "" "" c_dwgname
         c_class c_item (strcat (ch-size ghk) (chr 34))  i_qty c_disc c_itemno r-ghk
     )
     (command "insert" "c:/ghk/iso/ghkiso" i_pnt  "" "" "" c_dwgname
         c_class c_item (strcat (rtos ghk 2 0) "A")  i_qty c_disc c_itemno r-ghk
     )
 )
)

(defun bmlist4(i_pnt i_size i_qty / r-ghk)
 (setvar "cmdecho" 0)
 (setvar "attdia" 0)
 (setq r-ghk "015")
 (command "layer" "s" "ghkiso" "")
 (command "insert" "c:/ghk/iso/ghkiso" i_pnt  "" "" "" c_dwgname
                            c_class c_item i_size i_qty c_disc c_itemno r-ghk)
)

(defun ssspec(/ lst1 lst2 lst21 list1 ok)
    (setq dcl_id (load_dialog "c:/ghk/iso/ssspec.dcl"))
    (if (not (new_dialog "ssspec" dcl_id))
        (exit)
    )
    (sslist1 "ssspec")
    (setq   list1 "0")
    (setq   c_class (nth 0 lst1))
    (action_tile "z_list"  "(sub_1 (setq list1 $value))")
    (start_list "z_list")
    (mapcar 'add_list lst1)
    (end_list)
    (setq ok(start_dialog))
    (done_dialog)
    (unload_dialog dcl_id)
    (if (/= dwgtype "D")(isobase1))
    (princ)
)

(defun sub_1(data)
    (setq   c_class (nth (atoi data)   lst1))
    (setq   lst21   (nth (atoi data)   lst2))
    (setq   rat     (nth 0 lst21))
    (setq   rat-txt (nth 1 lst21))
    (sslist2 c_class)
    (setq bmlst1- (nth 0 bmlst1))
    (setq endtype (atof (nth 0 bmlst1-)))
)

(defun ssbolt1(/ lst1 lst2 b-lst1 b-lst2 b-lst20 b-ghk)
    (setq dcl_id (load_dialog "c:/ghk/iso/ssspec.dcl"))
    (if (not (new_dialog "ssbolt" dcl_id))
        (exit)
    )
    (sslist1 "bolt")
    (setq b-ghk (strcat (ch-size ghk) (chr 34)))
    (setq b-lst1(nth (atoi sizenum) lst1))
    (setq b-lst2(nth (atoi sizenum) lst2))
    (if (not lenadd) (setq lenadd "100")  (if (/= lenadd  "100")  (setq lenadd lenadd)))
    (cond
        ((= rat "A")
            (setq b-lst20(nth 0 b-lst2))
        )
        ((= rat "B")
            (setq b-lst20(nth 1 b-lst2))
        )
        ((= rat "C")
            (setq b-lst20(nth 2 b-lst2))
        )
        ((= rat "D")
            (setq b-lst20(nth 3 b-lst2))
        )
        ((= rat "E")
            (setq b-lst20(nth 4 b-lst2))
        )
        ((= rat "F")
            (setq b-lst20(nth 5 b-lst2))
        )
    )
    (setq b-qty(nth 0 b-lst20))
    (setq b-size(nth 1 b-lst20))
    (setq c_itemno "081")
    (sc1)
    (cond
        ((= sd "M")
            (setq b-len(nth 2 b-lst20))
        )
        ((= sd "S")
            (setq b-len(nth 3 b-lst20))
        )
    )
    (action_tile "zghk"    "(setq b-ghk $value)")
    (action_tile "zqty"    "(setq b-qty $value)")
    (action_tile "zsize"   "(setq b-size $value)")
    (action_tile "zlen"    "(setq b-len $value)")
    (action_tile "zlenadd" "(setq lenadd $value)")
    (set_tile "zghk" b-ghk)
    (set_tile "zqty" b-qty)
    (set_tile "zsize" b-size)
    (set_tile "zlen" b-len)
    (set_tile "zlenadd" lenadd)
    (setq ok(start_dialog))
    (done_dialog)
    (unload_dialog dcl_id)
    (princ)
)

(defun ssbolt2(/ lst1 lst2 b-lst1 b-lst2 b-lst20)
    (sslist1 "bolt")
    (setq b-ghk (strcat (ch-size ghk) (chr 34)))
    (setq b-lst1(nth (atoi sizenum) lst1))
    (setq b-lst2(nth (atoi sizenum) lst2))
    (cond
        ((= rat "A")
            (setq b-lst20(nth 0 b-lst2))
        )
        ((= rat "B")
            (setq b-lst20(nth 1 b-lst2))
        )
        ((= rat "C")
            (setq b-lst20(nth 2 b-lst2))
        )
        ((= rat "D")
            (setq b-lst20(nth 3 b-lst2))
        )
        ((= rat "E")
            (setq b-lst20(nth 4 b-lst2))
        )
        ((= rat "F")
            (setq b-lst20(nth 5 b-lst2))
        )
    )
    (setq b-qty(nth 0 b-lst20))
    (setq b-size(nth 1 b-lst20))
    (setq c_itemno "081")
    (sc1)
    (cond
        ((= sd "M")
            (setq b-len(nth 2 b-lst20))
        )
        ((= sd "S")
            (setq b-len(nth 3 b-lst20))
        )
    )
)

(defun sc1(/ bmlst1 bmlst2 bmlst1- i_sock 1_weld i_large bmlst2- bmlst20-
             bmlst21- )
    (sslist2 c_class)
    (setq c_disc "")
    (setq bmlst1- (nth (atoi (substr c_itemno 1 2)) bmlst1))
    (setq i_sock (nth 0 bmlst1-))
    (setq i_weld (nth 1 bmlst1-))
    (setq i_large (nth 2 bmlst1-))
    (setq bmlst2- (nth (atoi (substr c_itemno 1 2)) bmlst2))
    (setq bmlst20- (nth 0 bmlst2-))
    (setq bmlst21- (nth 1 bmlst2-))
    (setq endtype (atoi(nth 0 bmlst1-)))
    (if (and (> ghk 0) (<= ghk (atof i_sock)))
        (setq c_disc (nth 0 bmlst20-))
        (if (and (>= ghk (atof i_sock)) (<= ghk (atof i_weld)))
            (setq c_disc (nth 1 bmlst20-))
            (if (and (>= ghk (atof i_weld)) (<= ghk (atof i_large)))
                (setq c_disc (nth 2 bmlst20-))
            )
        )
    )
    (if (and (> ghk 0) (<= ghk (atof i_sock)))
        (setq sd (nth 0 bmlst21-))
        (if (and (>= ghk (atof i_sock)) (<= ghk (atof i_weld)))
            (setq sd (nth 1 bmlst21-))
            (if (and (>= ghk (atof i_weld)) (<= ghk (atof i_large)))
                (setq sd (nth 2 bmlst21-))
            )
        )
    )
)

(defun ftof(/ sizenum1 chsize1 ftofnum fitlen ell90 ell90q ell90s ell90sq
              ell45 ell45q lentee lenteeq lenred lenredq lst1 lst2 pipe-size
              lst2-)
 (setq dcl_id (load_dialog "c:/ghk/iso/ssspec.dcl"))
  (if (not (new_dialog "ftof" dcl_id))
      (exit)
  )
 (sslist1 "fitting")
 (setq sizenum1 sizenum)
 (setq chsize1 chsize)
 (ch-size (atoi t-sizeno))
 (setq ftofnum (rtos (- (atoi sizenum) 7) 2 0))
 (setq pipe-size (nth (atoi ftofnum) lst1))
 (setq lst2- (nth (atoi ftofnum) lst2))
 (setq fitlen n-len)
 (setq ell90(nth 0 lst2-))
 (setq ell90q "0")
 (setq ell90s(nth 1 lst2-))
 (setq ell90sq "0")
 (setq ell45(nth 2 lst2-))
 (setq ell45q "0")
 (setq lentee(nth 3 lst2-))
 (setq lenteeq "0")
 (setq lenred(nth 4 lst2-))
 (setq lenredq "0")
 (action_tile "zpipe-size" "(setq pipe-size $value)")
 (action_tile "mainsize"   "(ftof_1 (setq ftofnum $value))")
 (action_tile "zfitlen"    "(setq fitlen $value)")
 (action_tile "zell90"     "(setq ell90 $value)")
 (action_tile "zell90q"    "(setq ell90q $value)")
 (action_tile "zell90s"    "(setq ell90s $value)")
 (action_tile "zell90sq"   "(setq ell90sq $value)")
 (action_tile "zell45"     "(setq ell45 $value)")
 (action_tile "zell45q"    "(setq ell45q $value)")
 (action_tile "zlentee"    "(setq lentee $value)")
 (action_tile "zlenteeq"   "(setq lenteeq $value)")
 (action_tile "zlenred"    "(setq lenred $value)")
 (action_tile "zlenredq"   "(setq lenredq $value)")
 (start_list "mainsize")
 (mapcar 'add_list lst1)
 (end_list)
 (set_tile "mainsize" ftofnum)
 (set_tile "zpipe-size" pipe-size)
 (set_tile "zfitlen"  fitlen)
 (set_tile "zell90"   ell90)
 (set_tile "zell90q"  ell90q)
 (set_tile "zell90s"  ell90s)
 (set_tile "zell90sq" ell90sq)
 (set_tile "zell45"   ell45)
 (set_tile "zell45q"  ell45q)
 (set_tile "zlentee"  lentee)
 (set_tile "zlenteeq" lenteeq)
 (set_tile "zlenred"  lenred)
 (set_tile "zlenredq" lenredq)
 (setq sizenum sizenum1)
 (setq chsize chsize1)
 (setq ok(start_dialog))
 (done_dialog)
 (unload_dialog dcl_id)
 (if (= ok 1)(ftof_2))
 (princ)
)

(defun ftof_1(data)
    (setq pipe-size (nth (atoi data) lst1))
    (setq lst2- (nth (atoi data) lst2))
    (setq ell90(nth 0 lst2-))
    (setq ell90s(nth 1 lst2-))
    (setq ell45(nth 2 lst2-))
    (setq lentee(nth 3 lst2-))
    (setq lenred(nth 4 lst2-))
    (set_tile "zpipe-size" pipe-size)
    (set_tile "zfitlen"  fitlen)
    (set_tile "zell90"   ell90)
    (set_tile "zell90q"  ell90q)
    (set_tile "zell90s"  ell90s)
    (set_tile "zell90sq" ell90sq)
    (set_tile "zell45"   ell45)
    (set_tile "zell45q"  ell45q)
    (set_tile "zlentee"  lentee)
    (set_tile "zlenteeq" lenteeq)
    (set_tile "zlenred"  lenred)
    (set_tile "zlenredq" lenredq)
)

(defun ftof_2()
    (setq n-len(rtos (- (atoi fitlen) (+
                    (* (atoi ell90)  (atoi ell90q))
                    (* (atoi ell90s) (atoi ell90sq))
                    (* (atoi ell45)  (atoi ell45q))
                    (* (atoi lentee) (atoi lenteeq))
                    (* (atoi lenred) (atoi lenredq))
                )) 2 0)
    )
)

(defun ssbolt3(/ boltlen len_last add_len len-fst)
    (setq b-len(rtos (+ (atof b-len) (atof lenadd)) 2 0))
    (setq boltlen(strlen b-len))
    (setq len_last(atof (substr b-len boltlen)))
    (setq add_len(- 10 len_last))
    (if (<= 8 add_len)
        (setq b-len(rtos (- (atof b-len) len_last) 2 0))
        (if (<= 3 add_len)
            (progn
                (setq len-fst(substr b-len 1 (- boltlen 1)))
                (setq b-len(strcat len-fst "5"))
            )
            (setq b-len(rtos (+ (atof b-len) add_len) 2 0))
        )
    )
)

(defun isomenuset()
    (setq dcl_id (load_dialog "c:/ghk/iso/valist.dcl"))
    (if (not old_point)(setq old_point '(640 480)))
    (if (not (new_dialog "menuset" dcl_id "" old_point))
        (exit)
    )
    (start_image "image1")
    (slide_image 0 0 (dimx_tile "image1") (dimy_tile "image1") "c:/ghk/iso/con-type")
    (end_image)
    (start_image "image2")
    (slide_image 0 0 (dimx_tile "image2") (dimy_tile "image2") "c:/ghk/iso/handwhil")
    (end_image)
    (start_image "image3")
    (slide_image 0 0 (dimx_tile "image3") (dimy_tile "image3") "c:/ghk/iso/txt-stl")
    (end_image)
    (start_image "image4")
    (slide_image 0 0 (dimx_tile "image4") (dimy_tile "image4") "c:/ghk/iso/valend")
    (end_image)
    (cond ((= 1 con-type) (set_tile "zcon1" "1"))
          ((= 2 con-type) (set_tile "zcon2" "1"))
    )
    (cond ((= 1 hand-type) (set_tile "zhand1" "1"))
          ((= 2 hand-type) (set_tile "zhand2" "1"))
    )
    (cond ((= 1 size-type) (set_tile "zsize1" "1"))
          ((= 2 size-type) (set_tile "zsize2" "1"))
    )
    (cond ((= 1 valend-type) (set_tile "zvalend1" "1"))
          ((= 2 valend-type) (set_tile "zvalend2" "1"))
    )
    (cond ((= 1 text-type) (set_tile "ztext1" "1"))
          ((= 2 text-type) (set_tile "ztext2" "1"))
    )
    (pset-s1)
    (action_tile "accept" "(progn (setq x $x y $y) (setq old_point (done_dialog 1)))")
    (action_tile "ansicode" "(setq ansi- 1 ks- 0)(pset-s1)")
    (action_tile "kscode"   "(setq ansi- 0 ks- 1)(pset-s1)")
    (action_tile "zhand1" "(setq hand-type 1)")
    (action_tile "zhand2" "(setq hand-type 2)")
    (action_tile "zsize1" "(setq size-type 1)")
    (action_tile "zsize2" "(setq size-type 2)")
    (action_tile "zcon1" "(setq con-type 1)")
    (action_tile "zcon2" "(setq con-type 2)")
    (action_tile "ztext1" "(setq text-type 1)")
    (action_tile "ztext2" "(setq text-type 2)")
    (action_tile "zvalend1" "(setq valend-type 1)")
    (action_tile "zvalend2" "(setq valend-type 2)")
    (setq ok(start_dialog))
    (done_dialog)
    (unload_dialog dcl_id)
    (if (= ok 1)(isobase1))
    (princ)
)

(defun pset-s1()
 (if (= 1 ks-)
      (set_tile "kscode" "1")
      (set_tile "ansicode" "1")
 )
)

(defun control(/ wlist)
    (setq dcl_id (load_dialog "c:/ghk/iso/valist.dcl"))
    (if (not old_point)(setq old_point '(640 480)))
    (if (not (new_dialog "valist" dcl_id "" old_point))
        (exit)
    )
    (setq wlist
        (list  "    Gate VA"
               "    Glove VA"
               "    Check VA"
               "     Ball VA"
               "    Butter VA"
               "     Dia. VA"
               "    Needle VA"
               "     3 WAY VA"
               "     Pinch VA"
        )
    )
    (if (not num1)(setq num1 "0"))
    (setq con-val 1)
    (cond ((= 1 future) (set_tile "zfuture1" "1"))
          ((= 0 future) (set_tile "zfuture2" "1"))
    )
    (action_tile "accept" "(progn (setq x $x y $y) (setq old_point (done_dialog 1)))")
    (action_tile "itemlist" "(control- (setq num1 $value))")
    (action_tile "zfuture1" "(setq future 1)(setq p-wedth1 (* 0.2 sk1))(setq p-wedth2 (* 0.3 sk1))(setq p-wedth3 (* 0.5 sk1))(setq p-wedth4 (* 0.7 sk1))")
    (action_tile "zfuture2" "(setq future 0)(setq p-wedth1 (* 0.2 sk1))(setq p-wedth2 (* 0.3 sk1))(setq p-wedth3 (* 0.5 sk1))(setq p-wedth4 (* 0.7 sk1))")
    (start_list "itemlist")
    (mapcar 'add_list wlist)
    (end_list)
    (set_tile "itemlist" num1)
    (setq ok(start_dialog))
    (done_dialog)
    (unload_dialog dcl_id)
    (if (= ok 1)(control-1))
    (princ)
)

(defun control-(data)
    (setq vasel1 (+ (atoi data) 1))
)

(defun control-1()
    (setq job_direc 2)
    (if (= vasel1 nil)(setq vasel1 1))
    (cond
        ((= vasel1 1)
            (IF (NOT i-gate)(load"c:/ghk/iso/i-valve"))(i-gate)
        )
        ((= vasel1 2)
            (IF (NOT i-glov)(load"c:/ghk/iso/i-valve"))(i-glov)
        )
        ((= vasel1 3)
            (IF (NOT i-che)(load"c:/ghk/iso/i-valve"))(i-che)
        )
        ((= vasel1 4)
            (IF (NOT i-ball)(load"c:/ghk/iso/i-valve"))(i-ball)
        )
        ((= vasel1 5)
            (IF (NOT i-but)(load"c:/ghk/iso/i-valve"))(i-but)
        )
        ((= vasel1 6)
            (IF (NOT i-dia)(load"c:/ghk/iso/i-valve"))(i-dia)
        )
        ((= vasel1 7)
            (IF (NOT i-ndl)(load"c:/ghk/iso/i-valve"))(i-ndl)
        )
        ((= vasel1 8)
            (IF (NOT i-thway)(load"c:/ghk/iso/i-valve"))(i-thway)
        )
        ((= vasel1 9)
            (IF (NOT i-pinch)(load"c:/ghk/iso/i-valve"))(i-pinch)
        )
    )
    (setq con-val nil)
)

(defun val-acc(/ wlist)
    (setq dcl_id (load_dialog "c:/ghk/iso/valist.dcl"))
    (if (not old_point)(setq old_point '(640 480)))
    (if (not (new_dialog "valist" dcl_id "" old_point))
        (exit)
    )
    (setq wlist
        (list  "    Gate VA"
               "    Glove VA"
               "    End Nozzle"
               "    End Flange"
               "   Blind Flange"
               "    Butter VA"
               "     Ball VA"
               "    Check VA"
               "     Dia. VA"
               "    Safety VA"
               "    Control VA"
               "    Y-Straner"
               "    B-Straner"
               "    T-Straner"
               "       Trap"
               "    Spectacle"
               "    Needle VA"
               "     3 WAY VA"
               "    Pinch VA"
        )
    )
    (if (not num2)(setq num2 "0"))
    (cond ((= 1 future) (set_tile "zfuture1" "1"))
          ((= 0 future) (set_tile "zfuture2" "1"))
    )
    (action_tile "accept" "(progn (setq x $x y $y) (setq old_point (done_dialog 1)))")
    (action_tile "itemlist" "(valacc- (setq num2 $value))")
    (action_tile "zfuture1" "(setq future 1)(setq p-wedth1 (* 0.2 sk1))(setq p-wedth2 (* 0.3 sk1))(setq p-wedth3 (* 0.5 sk1))(setq p-wedth4 (* 0.7 sk1))")
    (action_tile "zfuture2" "(setq future 0)(setq p-wedth1 (* 0.2 sk1))(setq p-wedth2 (* 0.3 sk1))(setq p-wedth3 (* 0.5 sk1))(setq p-wedth4 (* 0.7 sk1))")
    (start_list "itemlist")
    (mapcar 'add_list wlist)
    (end_list)
    (set_tile "itemlist" num2)
    (setq ok(start_dialog))
    (done_dialog)
    (unload_dialog dcl_id)
    (if (= ok 1)(valacc-1))
    (princ)
)

(defun valacc-(data)
    (setq vasel1 (+ (atoi data) 1))
)

(defun valacc-1()
    (setq job_direc 2)
    (if (= vasel1 nil)(setq vasel1 1))
    (cond
        ((= vasel1 1)
            (IF (NOT i-gate)(load"c:/ghk/iso/i-valve"))(i-gate)
        )
        ((= vasel1 2)
            (IF (NOT i-glov)(load"c:/ghk/iso/i-valve"))(i-glov)
        )
        ((= vasel1 3)
            (IF (NOT i-flg4)(load"c:/ghk/iso/i-flg"))(i-flg4)
        )
        ((= vasel1 4)
            (IF (NOT i-flg1)(load"c:/ghk/iso/i-flg"))(i-flg1)
        )
        ((= vasel1 5)
            (IF (NOT i-flg2)(load"c:/ghk/iso/i-flg"))(i-flg2)
        )
        ((= vasel1 6)
            (IF (NOT i-but)(load"c:/ghk/iso/i-valve"))(i-but)
        )
        ((= vasel1 7)
            (IF (NOT i-ball)(load"c:/ghk/iso/i-valve"))(i-ball)
        )
        ((= vasel1 8)
            (IF (NOT i-che)(load"c:/ghk/iso/i-valve"))(i-che)
        )
        ((= vasel1 9)
            (IF (NOT i-dia)(load"c:/ghk/iso/i-valve"))(i-dia)
        )
        ((= vasel1 10)
            (IF (NOT i-safety)(load"c:/ghk/iso/i-valve"))(i-safety)
        )
        ((= vasel1 11)
            (control)
        )
        ((= vasel1 12)
            (IF (NOT i-ystr)(load"c:/ghk/iso/i-str"))(i-ystr)
        )
        ((= vasel1 13)
            (IF (NOT i-bstr)(load"c:/ghk/iso/i-str"))(i-bstr)
        )
        ((= vasel1 14)
            (IF (NOT i-tstr)(load"c:/ghk/iso/i-str"))(i-tstr)
        )
        ((= vasel1 15)
            (IF (NOT i-trap)(load"c:/ghk/iso/i-str"))(i-trap)
        )
        ((= vasel1 16)
            (IF (NOT i-flg5)(load"c:/ghk/iso/i-flg"))(i-flg5)
        )
        ((= vasel1 17)
            (IF (NOT i-ndl)(load"c:/ghk/iso/i-valve"))(i-ndl)
        )
        ((= vasel1 18)
            (IF (NOT i-thway)(load"c:/ghk/iso/i-valve"))(i-thway)
        )
        ((= vasel1 19)
            (IF (NOT i-pinch)(load"c:/ghk/iso/i-valve"))(i-pinch)
        )
    )
)

(defun val-acc1(/ wlist);;male
    (setq dcl_id (load_dialog "c:/ghk/iso/valist.dcl"))
    (if (not old_point)(setq old_point '(640 480)))
    (if (not (new_dialog "valist" dcl_id "" old_point))
        (exit)
    )
    (setq wlist
        (list   "     PIPE"
                "     PLUG"
                "  CRE Large End     "
                "  CRE Small End     "
                "  ERE Large End     "
                "  ERE Small End     "
                "      Nipple    "
        )
    )
    (if (not num3)(setq num3 "0"))
    (cond ((= 1 future) (set_tile "zfuture1" "1"))
          ((= 0 future) (set_tile "zfuture2" "1"))
    )
    (action_tile "accept" "(progn (setq x $x y $y) (setq old_point (done_dialog 1)))")
    (action_tile "itemlist" "(valacc1- (setq num3 $value))")
    (action_tile "zfuture1" "(setq future 1)(setq p-wedth1 (* 0.2 sk1))(setq p-wedth2 (* 0.3 sk1))(setq p-wedth3 (* 0.5 sk1))(setq p-wedth4 (* 0.7 sk1))")
    (action_tile "zfuture2" "(setq future 0)(setq p-wedth1 (* 0.2 sk1))(setq p-wedth2 (* 0.3 sk1))(setq p-wedth3 (* 0.5 sk1))(setq p-wedth4 (* 0.7 sk1))")
    (start_list "itemlist")
    (mapcar 'add_list wlist)
    (end_list)
    (set_tile "itemlist" num3)
    (setq ok(start_dialog))
    (done_dialog)
    (unload_dialog dcl_id)
    (if (= ok 1)(valacc1-1))
    (princ)
)

(defun valacc1-(data)
    (setq fttsel1 (+ (atoi data) 1))
)

(defun valacc1-1()
   (setq job_direc 2)
    (if (= fttsel1 nil)(setq fttsel1 1))
   (cond
       ((= fttsel1 1)
           (IF (not i-pipe)(load"c:/ghk/iso/i-pipe"))(i-pipe)
       )
       ((= fttsel1 2)
           (IF (not i-plg)(load"c:/ghk/iso/fitting"))(i-plg)
       )
       ((= fttsel1 3)
            (IF (not i-swg1)(load"c:/ghk/iso/i-red"))(setq swg-type 1)(i-swg1)
       )
       ((= fttsel1 4)
            (IF (not i-swg2)(load"c:/ghk/iso/i-red"))(setq swg-type 2)(i-swg2)
       )
       ((= fttsel1 5)
            (IF (not i-swg1)(load"c:/ghk/iso/i-red"))(setq swg-type 3)(i-swg1)
       )
       ((= fttsel1 6)
            (IF (not i-swg2)(load"c:/ghk/iso/i-red"))(setq swg-type 4)(i-swg2)
       )
       ((= fttsel1 7)
            (IF (not i-nip)(load"c:/ghk/iso/fitting"))(i-nip)
       )
   )
)

(defun val-acc2(/ wlist)
    (setq dcl_id (load_dialog "c:/ghk/iso/valist.dcl"))
    (if (not old_point)(setq old_point '(640 480)))
    (if (not (new_dialog "valist" dcl_id "" old_point))
        (exit)
    )
    (setq wlist
        (list   "       PIPE          "
                "      90ELBOW         "
                "      45ELBOW         "
                "    TEE Straight      "
                "    TEE Brenct       "
                " Red TEE Straight"
                "  Red TEE Brenct    "
                "  CRE Large End     "
                "  CRE Small End     "
                "  ERE Large End     "
                "  ERE Small End     "
                "   Start Flange     "
        )
    )
    (if (not num4)(setq num4 "0"))
    (cond ((= 1 future) (set_tile "zfuture1" "1"))
          ((= 0 future) (set_tile "zfuture2" "1"))
    )
    (action_tile "accept" "(progn (setq x $x y $y) (setq old_point (done_dialog 1)))")
    (action_tile "itemlist" "(valacc2- (setq num4 $value))")
    (action_tile "zfuture1" "(setq future 1)(setq p-wedth1 (* 0.2 sk1))(setq p-wedth2 (* 0.3 sk1))(setq p-wedth3 (* 0.5 sk1))(setq p-wedth4 (* 0.7 sk1))")
    (action_tile "zfuture2" "(setq future 0)(setq p-wedth1 (* 0.2 sk1))(setq p-wedth2 (* 0.3 sk1))(setq p-wedth3 (* 0.5 sk1))(setq p-wedth4 (* 0.7 sk1))")
    (start_list "itemlist")
    (mapcar 'add_list wlist)
    (end_list)
    (set_tile "itemlist" num4)
    (setq ok(start_dialog))
    (done_dialog)
    (unload_dialog dcl_id)
    (if (= ok 1)(valacc2-1))
    (princ)
)
(defun valacc2-(data)
    (setq fttsel2 (+ (atoi data) 1))
)

(defun valacc2-1()
    (setq job_direc 2)
    (if (= fttsel2 nil)(setq fttsel2 1))
    (cond
        ((= fttsel2 1)
            (IF (not i-pipe)(load"c:/ghk/iso/i-pipe"))(i-pipe)
        )
        ((= fttsel2 2)
            (IF (not i-90elbow)(load"c:/ghk/iso/i-elbow"))(setq v-point 1)(i-90elbow)
        )
        ((= fttsel2 3)
            (IF (not i-45elbow)(load"c:/ghk/iso/i-elbow"))(setq v-point 1)(i-45elbow)
        )
        ((= fttsel2 4)
            (IF (not i-tee1)(load"c:/ghk/iso/i-tee"))(i-tee1)
        )
        ((= fttsel2 5)
            (IF (not i-tee2)(load"c:/ghk/iso/i-tee"))(i-tee2)
        )
        ((= fttsel2 6)
            (IF (not i-tee3)(load"c:/ghk/iso/i-tee"))(i-tee3)
        )
        ((= fttsel2 7)
            (IF (not i-tee4)(load"c:/ghk/iso/i-tee"))(i-tee4)
        )
        ((= fttsel2 8)
            (IF (not i-swg1)(load"c:/ghk/iso/i-red"))(setq swg-type 1)(i-swg1)
        )
        ((= fttsel2 9)
            (IF (not i-swg2)(load"c:/ghk/iso/i-red"))(setq swg-type 2)(i-swg2)
        )
        ((= fttsel2 10)
            (IF (not i-swg1)(load"c:/ghk/iso/i-red"))(setq swg-type 3)(i-swg1)
        )
        ((= fttsel2 11)
            (IF (not i-swg2)(load"c:/ghk/iso/i-red"))(setq swg-type 4)(i-swg2)
        )
        ((= fttsel2 12)
            (IF (NOT i-flg)(load"c:/ghk/iso/i-flg"))(i-flg)
        )
    )
)

(defun val-acc3(/ wlist);;female
    (setq dcl_id (load_dialog "c:/ghk/iso/valist.dcl"))
    (if (not old_point)(setq old_point '(640 480)))
    (if (not (new_dialog "valist" dcl_id "" old_point))
        (exit)
    )
    (setq wlist
        (list   "    90ELBOW     "
                "    45ELBOW     "
                "  TEE Straight  "
                "   TEE Brenct   "
                "Red TEE Straight"
                " Red TEE Brenct "
                "     Union      "
                "    Full Coup.  "
                "       Cap      "
                "     Gate VA    "
                "    Glove VA    "
                "    Chack VA    "
                "     Ball VA    "
                "    Steam Trap  "
                "   Start Flange "
                "   Vent & Drain "
                "     PI valve   "
        )
    )
    (if (not num5)(setq num5 "0"))
    (cond ((= 1 future) (set_tile "zfuture1" "1"))
          ((= 0 future) (set_tile "zfuture2" "1"))
    )
    (action_tile "accept" "(progn (setq x $x y $y) (setq old_point (done_dialog 1)))")
    (action_tile "itemlist" "(valacc3- (setq num5 $value))")
    (action_tile "zfuture1" "(setq future 1)(setq p-wedth1 (* 0.2 sk1))(setq p-wedth2 (* 0.3 sk1))(setq p-wedth3 (* 0.5 sk1))(setq p-wedth4 (* 0.7 sk1))")
    (action_tile "zfuture2" "(setq future 0)(setq p-wedth1 (* 0.2 sk1))(setq p-wedth2 (* 0.3 sk1))(setq p-wedth3 (* 0.5 sk1))(setq p-wedth4 (* 0.7 sk1))")
    (start_list "itemlist")
    (mapcar 'add_list wlist)
    (end_list)
    (set_tile "itemlist" num5)
    (setq ok(start_dialog))
    (done_dialog)
    (unload_dialog dcl_id)
    (if (= ok 1)(valacc3-1))
    (princ)
)
(defun valacc3-(data)
    (setq fttsel3 (+ (atoi data) 1))
)

(defun valacc3-1()
    (setq job_direc 2)
    (if (= fttsel3 nil)(setq fttsel3 1))
    (cond
        ((= fttsel3 1)
            (IF (not i-90elbow)(load"c:/ghk/iso/i-elbow"))(setq v-point 1)(i-90elbow)
        )
        ((= fttsel3 2)
            (IF (not i-45elbow)(load"c:/ghk/iso/i-elbow"))(setq v-point 1)(i-45elbow)
        )
        ((= fttsel3 3)
            (IF (not i-tee1)(load"c:/ghk/iso/i-tee"))(i-tee1)
        )
        ((= fttsel3 4)
            (IF (not i-tee2)(load"c:/ghk/iso/i-tee"))(i-tee2)
        )
        ((= fttsel3 5)
            (IF (not i-tee3)(load"c:/ghk/iso/i-tee"))(i-tee3)
        )
        ((= fttsel3 6)
            (IF (not i-tee4)(load"c:/ghk/iso/i-tee"))(i-tee4)
        )
        ((= fttsel3 7)
            (IF (not i-uni)(load"c:/ghk/iso/fitting"))(i-uni)
        )
        ((= fttsel3 8)
            (IF (not i-fcp)(load"c:/ghk/iso/fitting"))(i-fcp)
        )
        ((= fttsel3 9)
            (IF (not i-cap)(load"c:/ghk/iso/fitting"))(i-cap)
        )
        ((= fttsel3 10)
            (IF (NOT i-gate)(load"c:/ghk/iso/i-valve"))(i-gate)
        )
        ((= fttsel3 11)
            (IF (NOT i-glov)(load"c:/ghk/iso/i-valve"))(i-glov)
        )
        ((= fttsel3 12)
            (IF (NOT i-che)(load"c:/ghk/iso/i-valve"))(i-che)
        )
        ((= fttsel3 13)
            (IF (NOT i-ball)(load"c:/ghk/iso/i-valve"))(i-ball)
        )
        ((= fttsel3 14)
            (IF (NOT i-trap)(load"c:/ghk/iso/i-str"))(i-trap)
        )
        ((= fttsel3 15)
            (IF (NOT i-flg)(load"c:/ghk/iso/i-flg"))(i-flg)
        )
        ((= fttsel3 16)
            (val-acc4)
        )
        ((= fttsel3 17)
            (val-acc5)
        )
    )
)

(defun val-acc4(/ wlist);;VENT & DRAIN
    (setq dcl_id (load_dialog "c:/ghk/iso/valist.dcl"))
    (if (not old_point)(setq old_point '(640 480)))
    (if (not (new_dialog "valist" dcl_id "" old_point))
        (exit)
    )
    (setq wlist
        (list   "     Gate VA    "
                "    Glove VA    "
        )
    )
    (if (not num6)(setq num6 "0"))
    (cond ((= 1 future) (set_tile "zfuture1" "1"))
          ((= 0 future) (set_tile "zfuture2" "1"))
    )
    (action_tile "accept" "(progn (setq x $x y $y) (setq old_point (done_dialog 1)))")
    (action_tile "itemlist" "(valacc4- (setq num6 $value))")
    (action_tile "zfuture1" "(setq future 1)(setq p-wedth1 (* 0.2 sk1))(setq p-wedth2 (* 0.3 sk1))(setq p-wedth3 (* 0.5 sk1))(setq p-wedth4 (* 0.7 sk1))")
    (action_tile "zfuture2" "(setq future 0)(setq p-wedth1 (* 0.2 sk1))(setq p-wedth2 (* 0.3 sk1))(setq p-wedth3 (* 0.5 sk1))(setq p-wedth4 (* 0.7 sk1))")
    (start_list "itemlist")
    (mapcar 'add_list wlist)
    (end_list)
    (set_tile "itemlist" num6)
    (setq ok(start_dialog))
    (done_dialog)
    (unload_dialog dcl_id)
    (if (= ok 1)(valacc4-1))
    (princ)
)
(defun valacc4-(data)
    (setq fttsel4 (+ (atoi data) 1))
)

(defun valacc4-1()
    (setq job_direc 2)
    (if (= fttsel4 nil)(setq fttsel4 1))
    (setq ventdr 1)
    (cond
        ((= fttsel4 1)
            (setq c_itemno "090")
            (sc1)
            (if (<= ghk endtype)
                (progn
                    (IF (NOT i-gate)(load"c:/ghk/iso/i-valve"))(i-gate)
                    (IF (not i-nip)(load"c:/ghk/iso/fitting"))(i-nip)
                    (IF (not i-cap)(load"c:/ghk/iso/fitting"))(i-cap)
                )
                (prompt "\nIS NOT SPEC SIZE ")
            )
        )
        ((= fttsel4 2)
            (setq c_itemno "100")
            (sc1)
            (if (<= ghk endtype)
                (progn
                    (IF (NOT i-glov)(load"c:/ghk/iso/i-valve"))(i-glov)
                    (IF (not i-nip)(load"c:/ghk/iso/fitting"))(i-nip)
                    (IF (not i-cap)(load"c:/ghk/iso/fitting"))(i-cap)
                )
                (prompt "\nIS NOT SPEC SIZE ")
            )
        )
    )
)

(defun val-acc5(/ wlist);;PI GAGE
    (setq dcl_id (load_dialog "c:/ghk/iso/valist.dcl"))
    (if (not old_point)(setq old_point '(640 480)))
    (if (not (new_dialog "valist" dcl_id "" old_point))
        (exit)
    )
    (setq wlist
        (list   "     Gate VA    "
                "    Glove VA    "
        )
    )
    (if (not num7)(setq num7 "0"))
    (cond ((= 1 future) (set_tile "zfuture1" "1"))
          ((= 0 future) (set_tile "zfuture2" "1"))
    )
    (action_tile "accept" "(progn (setq x $x y $y) (setq old_point (done_dialog 1)))")
    (action_tile "itemlist" "(valacc5- (setq num7 $value))")
    (action_tile "zfuture1" "(setq future 1)(setq p-wedth1 (* 0.2 sk1))(setq p-wedth2 (* 0.3 sk1))(setq p-wedth3 (* 0.5 sk1))(setq p-wedth4 (* 0.7 sk1))")
    (action_tile "zfuture2" "(setq future 0)(setq p-wedth1 (* 0.2 sk1))(setq p-wedth2 (* 0.3 sk1))(setq p-wedth3 (* 0.5 sk1))(setq p-wedth4 (* 0.7 sk1))")
    (start_list "itemlist")
    (mapcar 'add_list wlist)
    (end_list)
    (set_tile "itemlist" num7)
    (setq ok(start_dialog))
    (done_dialog)
    (unload_dialog dcl_id)
    (if (= ok 1)(valacc5-1))
    (princ)
)
(defun valacc5-(data)
    (setq fttsel5 (+ (atoi data) 1))
)

(defun valacc5-1()
    (setq job_direc 2)
    (if (= fttsel5 nil)(setq fttsel5 1))
    (setq ventdr 2)
    (cond
        ((= fttsel5 1)
            (setq c_itemno "090")
            (sc1)
            (IF (NOT i-gate)(load"c:/ghk/iso/i-valve"))
            (if (<= ghk endtype)
                (i-gate)
                (prompt "\nIS NOT SPEC SIZE ")
            )
        )
        ((= fttsel5 2)
            (setq c_itemno "100")
            (sc1)
            (IF (NOT i-glov)(load"c:/ghk/iso/i-valve"))
            (if (<= ghk endtype)
                (i-glov)
                (prompt "\nIS NOT SPEC SIZE ")
            )
        )
    )
    (setq ventdr nil)
)

(defun val-acc6(/ wlist)
    (setq dcl_id (load_dialog "c:/ghk/iso/valist.dcl"))
    (if (not old_point)(setq old_point '(640 480)))
    (if (not (new_dialog "valist" dcl_id "" old_point))
        (exit)
    )
    (setq wlist
        (list  "    End Flange"
               "   Blind Flange"
               "    Control VA"
        )
    )
    (if (not num8)(setq num8 "0"))
    (cond ((= 1 future) (set_tile "zfuture1" "1"))
          ((= 0 future) (set_tile "zfuture2" "1"))
    )
    (action_tile "accept" "(progn (setq x $x y $y) (setq old_point (done_dialog 1)))")
    (action_tile "itemlist" "(valacc6- (setq num8 $value))")
    (action_tile "zfuture1" "(setq future 1)(setq p-wedth1 (* 0.2 sk1))(setq p-wedth2 (* 0.3 sk1))(setq p-wedth3 (* 0.5 sk1))(setq p-wedth4 (* 0.7 sk1))")
    (action_tile "zfuture2" "(setq future 0)(setq p-wedth1 (* 0.2 sk1))(setq p-wedth2 (* 0.3 sk1))(setq p-wedth3 (* 0.5 sk1))(setq p-wedth4 (* 0.7 sk1))")
    (start_list "itemlist")
    (mapcar 'add_list wlist)
    (end_list)
    (set_tile "itemlist" num8)
    (setq ok(start_dialog))
    (done_dialog)
    (unload_dialog dcl_id)
    (if (= ok 1)(valacc6-1))
    (princ)
)

(defun valacc6-(data)
    (setq vasel1 (+ (atoi data) 1))
)

(defun valacc6-1()
    (setq job_direc 2)
    (if (= fttsel6 nil)(setq fttsel6 1))
    (if (= future 1)
        (progn
            (IF (not i-gas)(load"c:/ghk/iso/fitting"))(i-gas)
            (IF (not i-blt)(load"c:/ghk/iso/fitting"))(i-blt)
        )
    )
    (cond
        ((= vasel1 1)
            (IF (NOT i-flg1)(load"c:/ghk/iso/i-flg"))(i-flg1)
        )
        ((= vasel1 2)
            (IF (NOT i-flg2)(load"c:/ghk/iso/i-flg"))(i-flg2)
        )
        ((= vasel1 3)
            (control)
        )
    )
)


(defun disc-cha(ch1 ch2 / qty1 qty2 text1 text2 text3)
    (setq qty1 1)
    (setq qty2 1)
    (while qty1
        (setq text1 (substr c_disc qty2 (strlen ch1)))
        (if (= ch1 text1)
            (progn
               (setq text2 (substr c_disc 1 (- qty2 1)))
               (setq text3 (substr c_disc (+ qty2 (strlen ch1))))
               (setq c_disc (strcat text2 ch2 text3))
               (setq qty1 nil)
            )
            (progn
                (setq qty2 (+ qty2 1))
                (if (= qty2 (strlen c_disc))
                   (setq qty1 nil)
                )
            )
        )
    )
)

(defun ratchan()
    (if (/= rat1 nil)
        (cond
            ((= rat1 "A")
                (setq c_item (strcat c_item "1"))
                (disc-cha rat-txt "150#")
            )
            ((= rat1 "B")
                (setq c_item (strcat c_item "3"))
                (disc-cha rat-txt "300#")
            )
            ((= rat1 "C")
                (setq c_item (strcat c_item "6"))
                (disc-cha rat-txt "600#")
            )
            ((= rat1 "D")
                (setq c_item (strcat c_item "9"))
                (disc-cha rat-txt "900#")
            )
            ((= rat1 "E")
                (setq c_item (strcat c_item "15"))
                (disc-cha rat-txt "1500#")
            )
        )
    )
)

(defun C:ds(/ i sss l en el)
    (setvar "cmdecho" 0)
    (princ " DDATTE ")
    (setq i 0)
    (setq sss(ssget))
    (setq l(sslength sss))
    (repeat l
        (setq en(ssname sss i))
        (setq el (entget en))
        (if (AND (= "INSERT" (cdr (assoc 0 el))) (= "GHKISO" (cdr (assoc 2 el))))
            (command "ddatte" en)
        )
        (setq i(+ 1 i))
    )
)
(defun C:T1()
   (IF (not text1)(LOAD"c:/ghk/iso/textang"))
   (text1)
)
(defun C:T2()
   (IF (not text2)(LOAD"c:/ghk/iso/textang"))
   (text2)
)
(defun C:T3()
   (IF (not text3)(LOAD"c:/ghk/iso/textang"))
   (text3)
)
(defun C:T4()
   (IF (not text4)(LOAD"c:/ghk/iso/textang"))
   (text4)
)
(defun C:T5()
   (IF (not text5)(LOAD"c:/ghk/iso/textang"))
   (text5)
)
(defun C:T6()
   (IF (not text6)(LOAD"c:/ghk/iso/textang"))
   (text6)
)
(defun C:T7()
   (IF (not text7)(LOAD"c:/ghk/iso/textang"))
   (text7)
)
(defun C:T8()
   (IF (not text8)(LOAD"c:/ghk/iso/textang"))
   (text8)
)
(defun ch-size(i_pnt /)
    (cond
        ((= i_pnt   15)(setq sizenum  "0")(setq chsize "1/2"))
        ((= i_pnt   20)(setq sizenum  "1")(setq chsize "3/4"))
        ((= i_pnt   25)(setq sizenum  "2")(setq chsize "1"))
        ((= i_pnt   40)(setq sizenum  "3")(setq chsize "1 1/2"))
        ((= i_pnt   50)(setq sizenum  "4")(setq chsize "2"))
        ((= i_pnt   65)(setq sizenum  "5")(setq chsize "2 1/2"))
        ((= i_pnt   80)(setq sizenum  "6")(setq chsize "3"))
        ((= i_pnt  100)(setq sizenum  "7")(setq chsize "4"))
        ((= i_pnt  125)(setq sizenum  "8")(setq chsize "5"))
        ((= i_pnt  150)(setq sizenum  "9")(setq chsize "6"))
        ((= i_pnt  200)(setq sizenum "10")(setq chsize "8"))
        ((= i_pnt  250)(setq sizenum "11")(setq chsize "10"))
        ((= i_pnt  300)(setq sizenum "12")(setq chsize "12"))
        ((= i_pnt  350)(setq sizenum "13")(setq chsize "14"))
        ((= i_pnt  400)(setq sizenum "14")(setq chsize "16"))
        ((= i_pnt  450)(setq sizenum "15")(setq chsize "18"))
        ((= i_pnt  500)(setq sizenum "16")(setq chsize "20"))
        ((= i_pnt  550)(setq sizenum "17")(setq chsize "22"))
        ((= i_pnt  600)(setq sizenum "18")(setq chsize "24"))
        ((= i_pnt  650)(setq sizenum "19")(setq chsize "26"))
        ((= i_pnt  700)(setq sizenum "20")(setq chsize "28"))
        ((= i_pnt  750)(setq sizenum "21")(setq chsize "30"))
        ((= i_pnt  800)(setq sizenum "22")(setq chsize "32"))
        ((= i_pnt  850)(setq sizenum "23")(setq chsize "34"))
        ((= i_pnt  900)(setq sizenum "24")(setq chsize "36"))
        ((= i_pnt  950)(setq sizenum "25")(setq chsize "38"))
        ((= i_pnt 1000)(setq sizenum "26")(setq chsize "40"))
        ((= i_pnt 1050)(setq sizenum "27")(setq chsize "42"))
        ((= i_pnt 1100)(setq sizenum "28")(setq chsize "44"))
        ((= i_pnt 1150)(setq sizenum "29")(setq chsize "46"))
        ((= i_pnt 1200)(setq sizenum "30")(setq chsize "48"))
        ((= i_pnt 1250)(setq sizenum "31")(setq chsize "50"))
        ((= i_pnt 1300)(setq sizenum "32")(setq chsize "52"))
        ((= i_pnt 1350)(setq sizenum "33")(setq chsize "54"))
        ((= i_pnt 1400)(setq sizenum "34")(setq chsize "56"))
        ((= i_pnt 1450)(setq sizenum "35")(setq chsize "58"))
        ((= i_pnt 1500)(setq sizenum "36")(setq chsize "60"))
        ((= i_pnt 1650)(setq sizenum "37")(setq chsize "66"))
        ((= i_pnt 1800)(setq sizenum "38")(setq chsize "72"))
        ((= i_pnt   10)(setq sizenum "39")(setq chsize "3/8"))
    )
)

(defun ch-size1(i_pnt /)
    (cond
        ((= i_pnt "1/2"  )(setq n-len1  "015"))
        ((= i_pnt "3/4"  )(setq n-len1  "020"))
        ((= i_pnt "1"    )(setq n-len1  "025"))
        ((= i_pnt "1 1/2")(setq n-len1  "040"))
        ((= i_pnt "2"    )(setq n-len1  "050"))
        ((= i_pnt "2 1/2")(setq n-len1  "065"))
        ((= i_pnt "3"    )(setq n-len1  "080"))
        ((= i_pnt "4"    )(setq n-len1  "100"))
        ((= i_pnt "5"    )(setq n-len1  "125"))
        ((= i_pnt "6"    )(setq n-len1  "150"))
        ((= i_pnt "8"    )(setq n-len1  "200"))
        ((= i_pnt "10"   )(setq n-len1  "250"))
        ((= i_pnt "12"   )(setq n-len1  "300"))
        ((= i_pnt "14"   )(setq n-len1  "350"))
        ((= i_pnt "16"   )(setq n-len1  "400"))
        ((= i_pnt "18"   )(setq n-len1  "450"))
        ((= i_pnt "20"   )(setq n-len1  "500"))
        ((= i_pnt "22"   )(setq n-len1  "550"))
        ((= i_pnt "24"   )(setq n-len1  "600"))
        ((= i_pnt "26"   )(setq n-len1  "650"))
        ((= i_pnt "28"   )(setq n-len1  "700"))
        ((= i_pnt "30"   )(setq n-len1  "750"))
        ((= i_pnt "32"   )(setq n-len1  "800"))
        ((= i_pnt "34"   )(setq n-len1  "850"))
        ((= i_pnt "36"   )(setq n-len1  "900"))
        ((= i_pnt "38"   )(setq n-len1  "950"))
        ((= i_pnt "40"   )(setq n-len1 "1000"))
        ((= i_pnt "42"   )(setq n-len1 "1050"))
        ((= i_pnt "44"   )(setq n-len1 "1100"))
        ((= i_pnt "46"   )(setq n-len1 "1150"))
        ((= i_pnt "48"   )(setq n-len1 "1200"))
        ((= i_pnt "50"   )(setq n-len1 "1250"))
        ((= i_pnt "52"   )(setq n-len1 "1300"))
        ((= i_pnt "54"   )(setq n-len1 "1350"))
        ((= i_pnt "56"   )(setq n-len1 "1400"))
        ((= i_pnt "58"   )(setq n-len1 "1450"))
        ((= i_pnt "60"   )(setq n-len1 "1500"))
        ((= i_pnt "66"   )(setq n-len1 "1650"))
        ((= i_pnt "72"   )(setq n-len1 "1800"))
        ((= i_pnt "3/8"  )(setq n-len1 "010"))
    )
)

(setq s (getvar "dimscale"))
(setq sk1 (* 0.7 s))
(setq txt-h 2.5)
(setq p-wedth1 (* 0.2 sk1))
(setq p-wedth2 (* 0.3 sk1))
(setq p-wedth3 (* 0.5 sk1))
(setq p-wedth4 (* 0.7 sk1))
(setq dwgtype "I")
(if (not rat)(setq rat "A"))
(if (not sd)(setq sd "SO"))
(if (not future)(setq future 1))
(if (not smalls)(setq smalls 50))
(if (not c_class)(setq c_class "None"))
(if (not c_item)(setq c_item "None"))
(if (not con-type)(setq con-type 2))
(if (not hand-type)(setq hand-type 2))
(if (not size-type)(setq size-type 2))
(if (not valend-type)(setq valend-type 2))
(if (not text-type)(setq text-type 2))
(if (not ghk)(setq ghk 150))
