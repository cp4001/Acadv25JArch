(defun i-gate(/ flglen piplen pt1 pt2 pt1a pt1b pt1c pt1d pt2a pt2b
                pt2c pt2d ang ang1 ptw1)
    (setiso1)
    (setq c_item "GAT")
    (setq c_itemno "090")
    (sc1)
    (if (= con-val 1)(progn (setq sd "FLG")(setq sd-1 sd)))
    (set-selec i-gate1)
    (setiso2)
    (setq old_sd sd)
    (if (/= ventdr 1)(if (or (= sd "SW") (= sd "SCR'D"))(val-acc1)(if (=  sd "BW")(val-acc2)(val-acc))))
    (prin1)
)
(defun i-gate1()
    (if (= sd "FLG")(if (= job_direc 2)(progn (i-gas)(i-blt))))
    (setq c_item "GAT")
    (setq c_itemno "090")
    (sc1)
    (i-valve)
    (command "pline" (POLAR pt1 ang1 flglen) "w" "0" "0"
             (POLAR pt1 (+ ang1 (dtr 180)) flglen)
             (POLAR pt2 ang1 flglen)
             (POLAR pt2 (+ ang1 (dtr 180)) flglen) "c"
    )
    (if (= valend-type 1)
        (i-valve2)
    )
    (if (= ventdr 2)
        (if (/= sd "SCR'D")
            (progn
                (disc-cha sd "SW x SCR'D")
                (setq sd "SW x SCR'D")
                (setq c_item "GATD")
            )
        )
    )
    (ratchan)
    (if (and (= future 1)(= con-val nil))
        (if (/= dwgtype "D")(bmlist (POLAR pt1 ang (/ (distance pt1 pt2) 2))))
    )
    (i-while)
    (i-valve1)
)

(defun i-glov(/ flglen piplen pt1 pt2 pt1a pt1b pt1c pt1d pt2a pt2b pt2c
                pt2d ang ang1 ptw1)
    (setiso1)
    (setq c_item "GLO")
    (setq c_itemno "100")
    (sc1)
    (if (= con-val 1)(progn (setq sd "FLG")(setq sd-1 sd)))
    (set-selec i-glov1)
    (setiso2)
    (setq old_sd sd)
    (if (/= ventdr 1)(if (or (= sd "SW") (= sd "SCR'D"))(val-acc1)(if (=  sd "BW")(val-acc2)(val-acc))))
    (prin1)
)
(defun i-glov1()
    (if (= sd "FLG")(if (= job_direc 2)(progn (i-gas)(i-blt))))
    (setq c_item "GLO")
    (setq c_itemno "100")
    (sc1)
    (i-valve)
    (command "pline" (POLAR pt1 ang1 flglen) "w" "0" "0"
             (POLAR pt1 (+ ang1 (dtr 180)) flglen)
             (POLAR pt2 ang1 flglen)
             (POLAR pt2 (+ ang1 (dtr 180)) flglen) "c"
    )
    (if (= valend-type 1)
        (i-valve2)
    )
    (if (= ventdr 2)
        (if (/= sd "SCR'D")
            (progn
                (disc-cha sd "SW x SCR'D")
                (setq sd "SW x SCR'D")
                (setq c_item "GATD")
            )
        )
    )
    (ratchan)
    (if (and (= future 1)(= con-val nil))
        (if (/= dwgtype "D")(bmlist (POLAR pt1 ang (/ (distance pt1 pt2) 2))))
    )
    (i-while)
    (if (< ghk 49)
        (command "donut" "0" (* 2 sk1) ptw1 "")
        (command "donut" "0" (* 4 sk1) ptw1 "")
    )
    (i-valve1)
)

(defun i-ball(/ flglen piplen pt1 pt2 pt1a pt1b pt1c pt1d pt2a pt2b pt2c pt2d ang ang1 ptw1 ptw2 ptw3)
    (setiso1)
    (setq c_item "BAL")
    (setq c_itemno "120")
    (sc1)
    (if (= con-val 1)(progn (setq sd "FLG")(setq sd-1 sd)))
    (set-selec i-ball1)
    (setiso2)
    (setq old_sd sd)
    (if (or (= sd "SW") (= sd "SCR'D"))(val-acc1)(if (= sd "BW")(val-acc2)(val-acc)))
    (prin1)
)

(defun i-ball1()
    (if (= sd "FLG")(if (= job_direc 2)(progn (i-gas)(i-blt))))
    (setq c_item "BAL")
    (setq c_itemno "120")
    (sc1)
    (i-valve)
    (if (= sd "BW")
        (progn
            (setq pt1a (POLAR pt1 ang1 piplen))
            (setq pt1b (POLAR pt1 (+ ang1 (dtr 180)) piplen))
            (setq pt1c (POLAR pt1a ang piplen))
            (setq pt1d (POLAR pt1b ang piplen))
            (setq pt2a (POLAR (POLAR pt2 ang piplen) ang1 piplen))
            (setq pt2b (POLAR (POLAR pt2 ang piplen) (+ ang1 (dtr 180)) piplen))
            (setq pt2c (POLAR pt2a ang piplen))
            (setq pt2d (POLAR pt2b ang piplen))
            (setq pt1  (POLAR pt1 ang piplen))
            (setq pt2  (POLAR pt2 ang piplen))
            (command "line" pt1c pt1a pt1b pt1d "")
            (command "line" pt2a pt2c pt2d pt2b "")
        )
    )
    (command "pline" (POLAR pt1 ang1 flglen) "w" "0" "0"
             (POLAR pt1 (+ ang1 (dtr 180)) flglen)
             (POLAR pt2 ang1 flglen)
             (POLAR pt2 (+ ang1 (dtr 180)) flglen) "c"
    )
;    (if (or (and (= con-val nil) (= sd "SW")) (and (= con-val nil)(= sd "SCR'D")))
;    (if (<= ghk endtype)
        (if (< ghk 49)
        (progn
            (if (= valend-type 1)
                (i-valve2)
            )
            (setq ptw1 (POLAR pt1 ang (* 4 sk1)))
        )
        (progn
            (setq ptw1 (POLAR pt1 ang (* 5.5 sk1)))
            (setq ptw2 (POLAR ptw1 ang1 (* flglen 2)))
            (setq ptw3 (POLAR ptw2 ang flglen))
            (command "pline" ptw1 "w" "0" "0" ptw2 ptw3 "")
        )
    )
    (ratchan)
    (if (and (= future 1)(= con-val nil))
        (if (/= dwgtype "D")(bmlist (POLAR pt1 ang (/ (distance pt1 pt2) 2))))
    )
    (command "layer" "s" "1c" "")
    (if (< ghk 49)
        (command "circle" ptw1 (* 1 sk1))
        (command "circle" ptw1 (* 2 sk1))
    )
    (if (= sd "BW")
        (cond
            ((= future 1)
                (command "insert" "c:/ghk/iso/isoweld" (POLAR pt1 (+ ang (dtr 180)) piplen) sk1 "" "")
                (command "insert" "c:/ghk/iso/isoweld" (POLAR pt2 ang piplen) sk1 "" "")
            )
            ((= future 0)
                (command "layer" "s" "2h" "")
                (command "circle" (POLAR pt1 (+ ang (dtr 180)) piplen) sk1)
                (command "circle" (POLAR pt2 ang piplen) sk1)
            )
        )
    )
    (command "layer" "s" "1c" "")
    (command "line" (POLAR pt1 (+ ang (dtr 180)) (* 1.5 sk1)) (POLAR pt2 ang (* 1.5 sk1)) "")
    (if (= sd "BW")
        (setq endpoint (POLAR pt2 ang piplen))
        (setq endpoint (POLAR pt2 ang (* 0.75 sk1)))
    )
    (setq endang ang)
)

(defun i-che(/ flglen piplen pt1 pt2 pt1a pt1b pt1c pt1d pt2a pt2b pt2c pt2d pt3 pt4 pt5 pt5a pt5b ang ang1)
    (setiso1)
    (setq c_item "CHE")
    (setq c_itemno "110")
    (sc1)
    (if (= con-val 1)(progn (setq sd "FLG")(setq sd-1 sd)))
    (set-selec i-che1)
    (setiso2)
    (setq old_sd sd)
    (if (or (= sd "SW") (= sd "SCR'D"))(val-acc1)(if (= sd "BW")(val-acc2)(val-acc)))
    (prin1)
)
(defun i-che1()
    (if (= job_direc 2)(progn (if (or (= sd "FLG") (= sd "WAFER"))(i-gas))(if (= sd "FLG")(i-blt))))
    (setq c_item "CHE")
    (setq c_itemno "110")
    (sc1)
    (i-valve)
    (command "pline" (POLAR pt1 (+ ang1 (dtr 180)) flglen) "w" "0" "0"
             (POLAR pt1 ang1 flglen)
             (POLAR pt2 (+ ang1 (dtr 180)) flglen)
             (POLAR pt2 ang1 flglen) ""
    )
    (if (or (and (= con-val nil) (= sd "SW")) (and (= con-val nil)(= sd "SCR'D")))
        (progn
            (if (= valend-type 1)
                (i-valve2)
            )
            (setq pt3 (POLAR pt1 (+ ang1 (dtr 180)) (* 3 sk1)))
            (setq pt4 (POLAR pt2 (+ ang1 (dtr 180)) (* 3 sk1)))
        )
        (progn
            (setq pt3 (POLAR pt1 (+ ang1 (dtr 180)) (* 6 sk1)))
            (setq pt4 (POLAR pt2 (+ ang1 (dtr 180)) (* 6 sk1)))
        )
    )
    (setq pt5 (POLAR pt4 (+ ang  (dtr 180)) (* 2.5 sk1)))
    (setq pt5a(POLAR pt5 ang1 (* 0.6 sk1)))
    (setq pt5b(POLAR pt5 (+ ang1 (dtr 180)) (* 0.6 sk1)))
    (ratchan)
    (if (and (= future 1)(= con-val nil))
        (if (/= dwgtype "D")(bmlist (POLAR pt1 ang (/ (distance pt1 pt2) 2))))
    )
    (command "layer" "s" "1c" "")
    (command "line" pt3 pt4 "")
    (command "solid" pt4 pt5a pt5b "" "")
    (i-valve1)
)

(defun i-dia(/ flglen piplen pt1 pt2 pt1a pt1b pt1c pt1d pt2a pt2b pt2c pt2d ang ang1 ptw1)
    (setiso1)
    (setq c_item "DIA")
    (setq c_itemno "140")
    (sc1)
    (if (= con-val 1)(progn (setq sd "FLG")(setq sd-1 sd)))
    (set-selec i-dia1)
    (setiso2)
    (setq old_sd sd)
    (if (or (= sd "SW") (= sd "SCR'D"))(val-acc1)(if (= sd "BW")(val-acc2)(val-acc)))
    (prin1)
)
(defun i-dia1()
    (if (= sd "FLG")(if (= job_direc 2)(progn (i-gas)(i-blt))))
    (setq c_item "DIA")
    (setq c_itemno "140")
    (sc1)
    (i-valve)
    (command "pline" (POLAR pt1 ang1 flglen) "w" "0" "0"
             (POLAR pt1 (+ ang1 (dtr 180)) flglen)
             (POLAR pt2 ang1 flglen)
             (POLAR pt2 (+ ang1 (dtr 180)) flglen) "c")
    (if (or (and (= con-val nil) (= sd "SW")) (and (= con-val nil)(= sd "SCR'D")))
        (progn
            (command "arc" (POLAR pt1 ang1 flglen) (POLAR (POLAR pt1 ang (* 4 sk1)) ang1 (+ flglen (* 1.5 sk1))) (POLAR pt2 ang1 flglen))
            (if (= valend-type 1)
                (i-valve2)
            )
        )
        (command "arc" (POLAR pt1 ang1 flglen) (POLAR (POLAR pt1 ang (* 5.5 sk1)) ang1 (+ flglen (* 1.5 sk1))) (POLAR pt2 ang1 flglen))
    )
    (ratchan)
    (if (and (= future 1)(= con-val nil))
        (if (/= dwgtype "D")(bmlist (POLAR pt1 ang (/ (distance pt1 pt2) 2))))
    )
    (i-valve1)
)

(defun i-but(/ flglen piplen pt1 pt2 pt1a pt1b pt1c pt1d pt2a pt2b pt2c pt2d ang ang1 ptw1)
    (setiso1)
    (setq c_item "BUT")
    (setq c_itemno "130")
    (sc1)
    (if (= con-val 1)(progn (setq sd "FLG")(setq sd-1 sd)))
    (set-selec i-but1)
    (setq vallast 5)
    (setiso2)
    (setq old_sd sd)
    (if (or (= sd "SW") (= sd "SCR'D"))(val-acc1)(if (= sd "BW")(val-acc2)(val-acc)))
    (prin1)
)
(defun i-but1()
    (if (= job_direc 2)(progn (if (or (= sd "FLG") (= sd "WAFER"))(i-gas))(if (= sd "FLG")(i-blt))))
    (setq c_item "BUT")
    (setq c_itemno "130")
    (sc1)
    (if (= job_direc 1)
        (progn
            (setvar "osmode" 1)
            (SETQ pt1 (GETPOINT "\nPICK 1ST POINT OF VALVE : "))
            (IF (= pt1 nil)(setq pt1 endpoint))
            (setvar "osmode" 0)
            (setq ang (GETANGLE pt1 "\nPICK 2nd VALVE DIRECTION: "))
        )
    )
    (setvar "osmode" 0)
    (IF (= pt1 nil)(setq pt1 endpoint))
    (IF (= ang nil)(setq ang endang))
    (if (< ghk 49)
        (setq flglen (* 3 sk1))
        (setq flglen (* 5 sk1))
    )
    (if (= sd "BW")
        (setq pt1 pt1)
        (setq pt1 (POLAR pt1 ang (* 0.75 sk1)))
    )
    (setq pt2 (POLAR pt1 ang flglen))
    (initget 1)
    (setq ang1 (GETANGLE pt1 "\nPICK VALVE DIRECTION: "))
    (if (and (<= ang1 (+ ang (dtr 10))) (>= ang1 (- ang (dtr 10))))
        (setq ang1 (GETANGLE pt1 "\nPICK VALVE DIRECTION: "))
    )
    (if (= future 1)
        (command "layer" "s" "2c" "")
        (command "layer" "s" "2h" "")
    )
    (command "pline" (POLAR pt2 ang1 flglen) "w" "0" "0"
                     (POLAR pt1 ang1 flglen)
                     (POLAR pt1 (+ ang1 (dtr 180)) flglen)
                     (POLAR pt2 ang1 flglen)
                     (POLAR pt2 (+ ang1 (dtr 180)) flglen)
                     (POLAR pt1 (+ ang1 (dtr 180)) flglen) ""
    )
    (command "donut" "0" (* 1.5 sk1) (POLAR pt1 ang (/ flglen 2.0)) "")
    (ratchan)
    (if (and (= future 1)(= con-val nil))
        (if (/= dwgtype "D")(bmlist (POLAR pt1 ang (/ (distance pt1 pt2) 2))))
    )
    (i-valve1)
)


(defun i-safety(/ flglen pt1 pt2 pt3 ang ang1 pt1a pt1b pt3a pt3b pt4
                  pt4a pt4b pt5 pt5a pt5b pt6 pt6a pt6b pt7)
    (setiso1)
    (if (= job_direc 2)(progn (i-gas)(i-blt)))
    (setq c_itemno "090")
    (sc1)
    (setq tee-type 4)
    (ch-size ghk)
    (if (not i-rtee)(load"c:/ghk/iso/i-tee"))
    (i-rtee)
    (setq ghk br-size)
    (if (= job_direc 1)
        (progn
            (setvar "osmode" 1)
            (SETQ pt1 (GETPOINT "\nPICK 1ST POINT OF VALVE : "))
            (setvar "osmode" 0)
            (IF (= pt1 nil)(setq pt1 endpoint))
            (setq ang (GETANGLE pt1 "\nPICK 2nd VALVE DIRECTION: "))
        )
    )
    (setvar "osmode" 0)
    (IF (= ang nil)(setq ang endang))
    (IF (= pt1 nil)(setq pt1 endpoint))
    (if (< ghk 49)
        (progn
           (setq flglen (* 3 sk1))
           (setq pt1 (POLAR pt1 ang 0))
           (setq pt2 (POLAR pt1 ang (* 8 sk1)))
        )
        (progn
           (setq flglen (* 5 sk1))
           (setq pt1 (POLAR pt1 ang (* 0.75 sk1)))
           (setq pt2 (POLAR pt1 ang (* 11 sk1)))
        )
    )
    (initget 1)
    (setq ang1 (GETANGLE pt2 "\nPICK 3rd VALVE DIRECTION: "))
    (if (and (<= ang1 (+ ang (dtr 10))) (>= ang1 (- ang (dtr 10))))
        (setq ang1 (GETANGLE pt1 "\nPICK VALVE DIRECTION: "))
    )
    (if (< ghk 49)
        (setq pt3 (POLAR pt2 ang1 (* 8 sk1)))
        (setq pt3 (POLAR pt2 ang1 (* 11 sk1)))
    )
    (setq pt1a (POLAR pt1 (+ ang1 (dtr 180)) flglen))
    (setq pt1b (POLAR pt1 ang1 flglen))
    (setq pt3a (POLAR pt3 (+ ang (dtr 180)) flglen))
    (setq pt3b (POLAR pt3 ang flglen))
    (setq pt4  (POLAR pt2 ang (* flglen 1.5)))
    (setq pt4a (POLAR pt4 (+ ang1 (dtr 180)) (/ flglen 1.5)))
    (setq pt4b (POLAR pt4 ang1 (/ flglen 1.5)))
    (setq pt5  (POLAR pt4 ang (/ flglen 1.5)))
    (setq pt5a (POLAR pt5 (+ ang1 (dtr 180)) (/ flglen 1.5)))
    (setq pt5b (POLAR pt5 ang1 (/ flglen 1.5)))
    (setq pt6  (POLAR pt5 ang (/ flglen 1.5)))
    (setq pt6a (POLAR pt6 (+ ang1 (dtr 180)) (/ flglen 1.5)))
    (setq pt6b (POLAR pt6 ang1 (/ flglen 1.5)))
    (setq pt7  (POLAR pt6 ang (/ flglen 1.5)))
    (if (= future 1)
        (command "layer" "s" "2c" "")
        (command "layer" "s" "2h" "")
    )
    (command "pline" pt1a "w" "0" "0" pt2 pt3b pt3a pt2 pt1b pt1a "")
    (command "line" pt2 pt7 "" "line" pt4a pt4b "" "line" pt5a pt5b "" "line" pt6a pt6b "")
    (command "layer" "s" "1c" "")
    (command "line" (POLAR pt1 (+ ang (dtr 180)) (* 0.75 sk1)) pt2 (POLAR pt3 ang1 (* 0.75 sk1)) "")
    (if (< ghk 49)
        (setq endpoint pt3)
        (setq endpoint (POLAR pt3 ang1 (* 0.75 sk1)))
    )
    (setq endang ang1)
    (setiso2)
    (setq old_sd sd)
    (IF (not pi-tag)(load"c:/ghk/iso/fitting"))(pi-tag)
    (val-acc)
    (prin1)
)

(defun i-ndl(/ flglen piplen pt1 pt2 pt1a pt1b pt1c pt1d pt2a pt2b pt2c pt2d ang ang1 ptw1 ptw2 ptw3 ptw2a ptw2b
               ptw3a ptw3b)
    (setiso1)
    (setq c_item "NDL")
    (setq c_itemno "150")
    (sc1)
    (if (= con-val 1)(progn (setq sd "FLG")(setq sd-1 sd)))
    (set-selec i-ndl1)
    (setiso2)
    (setq old_sd sd)
    (if (or (= sd "SW") (= sd "SCR'D"))(val-acc1)(if (= sd "BW")(val-acc2)(val-acc)))
    (prin1)
)

(defun i-ndl1()
    (if (= sd "FLG")(if (= job_direc 2)(progn (i-gas)(i-blt))))
    (setq c_item "NDL")
    (setq c_itemno "150")
    (sc1)
    (i-valve)
    (command "pline" (POLAR pt1 ang1 flglen) "w" "0" "0"
             (POLAR pt1 (+ ang1 (dtr 180)) flglen)
             (POLAR pt2 ang1 flglen)
             (POLAR pt2 (+ ang1 (dtr 180)) flglen) "c"
    )
    (if (or (= sd "SW") (= sd "SCR'D"))
        (progn
            (if (= valend-type 1)(i-valve2))
            (setq ptw1 (POLAR pt1 ang (* 4 sk1)))
        )
        (setq ptw1 (POLAR pt1 ang (* 5.5 sk1)))
    )
    (setq ptw2 (POLAR ptw1 ang1 flglen))
    (setq ptw3 (POLAR ptw1 (+ ang1 (dtr 180)) flglen))
    (setq ptw2a(POLAR ptw2 ang (/ flglen 2)))
    (setq ptw2b(POLAR ptw2 (+ ang (dtr 180)) (/ flglen 2)))
    (setq ptw3a(POLAR ptw3 ang (/ flglen 2)))
    (setq ptw3b(POLAR ptw3 (+ ang (dtr 180)) (/ flglen 2)))
    (command "pline" ptw2a "w" "0" "0" ptw3a ptw3b ptw2b "c")
    (ratchan)
    (if (and (= future 1)(= con-val nil))
        (if (/= dwgtype "D")(bmlist (POLAR pt1 ang (/ (distance pt1 pt2) 2))))
    )
    (i-valve1)
)

(defun i-thway(/ flglen piplen pt1 pt2 ang ang1 ptw1 ptw2 ptw3 ptw2a ptw2b
                 pt1a pt1b pt1c pt1d pt2a pt2b pt2c pt2d ptw3a ptw3b)
    (setiso1)
    (setq c_item "3WAY")
    (setq c_itemno "160")
    (sc1)
    (if (= con-val 1)(progn (setq sd "FLG")(setq sd-1 sd)))
    (set-selec i-thway1)
    (setiso2)
    (setq old_sd sd)
    (if (or (= sd "SW") (= sd "SCR'D"))(val-acc1)(if (= sd "BW")(val-acc2)(val-acc)))
    (prin1)
)

(defun i-thway1()
    (if (= sd "FLG")(if (= job_direc 2)(progn (i-gas)(i-blt))))
    (setq c_item "3WAY")
    (setq c_itemno "160")
    (sc1)
    (i-valve)
    (command "pline" (POLAR pt1 ang1 flglen) "w" "0" "0"
             (POLAR pt1 (+ ang1 (dtr 180)) flglen)
             (POLAR pt2 ang1 flglen)
             (POLAR pt2 (+ ang1 (dtr 180)) flglen) "c"
    )
    (if (or (and (= con-val nil) (= sd "SW")) (and (= con-val nil)(= sd "SCR'D")))
        (progn
            (setq ptw1 (POLAR pt1 ang (* 4 sk1)))
            (setq ptw2 (POLAR ptw1 ang1 (* 8 sk1)))
            (if (= valend-type 1)(i-valve2))
            (command "pline" ptw2a "w" "0" "0" (POLAR ptw2a ang1 (* 1 sk1)) "")
            (command "pline" ptw2b "w" "0" "0" (POLAR ptw2b ang1 (* 1 sk1)) "")
        )
        (progn
            (setq ptw1 (POLAR pt1 ang (* 5.5 sk1)))
            (setq ptw2 (POLAR ptw1 ang1 (* 11 sk1)))
        )
    )
    (setq ptw2a(POLAR ptw2 ang flglen))
    (setq ptw2b(POLAR ptw2 (+ ang (dtr 180)) flglen))
    (command "pline" ptw1 "w" "0" "0" ptw2a ptw2b "c")
    (ratchan)
    (if (and (= future 1)(= con-val nil))
        (if (/= dwgtype "D")(bmlist (POLAR pt1 ang (/ (distance pt1 pt2) 2))))
    )
    (i-valve1)
)

(defun i-pinch(/ flglen piplen pt1 pt2 pt1a pt1b pt1c pt1d pt2a pt2b
                pt2c pt2d ang ang1 ptw1)
    (setiso1)
    (setq c_item "PIN")
    (setq c_itemno "180")
    (sc1)
    (if (= con-val 1)(progn (setq sd "FLG")(setq sd-1 sd)))
    (set-selec i-pinch1)
    (setiso2)
    (setq old_sd sd)
    (if (/= ventdr 1)(if (or (= sd "SW") (= sd "SCR'D"))(val-acc1)(if (=  sd "BW")(val-acc2)(val-acc))))
    (prin1)
)
(defun i-pinch1()
    (if (= sd "FLG")(if (= job_direc 2)(progn (i-gas)(i-blt))))
    (setq c_item "PIN")
    (setq c_itemno "180")
    (sc1)
    (i-valve)
    (command "pline" (POLAR pt1 ang1 flglen) "w" "0" "0"
             (POLAR pt2 ang1 flglen)
             (POLAR pt2 (+ ang1 (dtr 180)) flglen)
             (POLAR (polar pt1 ang (/ (distance pt1 pt2) 2.00)) ang1 flglen)
             (POLAR pt1 (+ ang1 (dtr 180)) flglen) "c"
    )
    (if (= valend-type 1)
        (i-valve2)
    )
    (ratchan)
    (if (and (= future 1)(= con-val nil))
        (if (/= dwgtype "D")(bmlist (POLAR pt1 ang (/ (distance pt1 pt2) 2))))
    )
    (i-valve1)
)

(defun i-valve()
    (if (= job_direc 1)
        (progn
            (setvar "osmode" 1)
            (SETQ pt1 (GETPOINT "\nPICK 1ST POINT OF VALVE : "))
            (IF (= pt1 nil)(setq pt1 endpoint))
            (setvar "osmode" 0)
            (setq ang (GETANGLE pt1 "\nPICK 2nd VALVE DIRECTION: "))
        )
    )
    (setvar "osmode" 0)
    (IF (= pt1 nil)(setq pt1 endpoint))
    (IF (= ang nil)(setq ang endang))
    (if (or (= sd "BW") (and (= sd "SW") (= valend-type 2) (= con-val nil)))
        (setq pt1 pt1)
        (setq pt1 (POLAR pt1 ang (* 0.75 sk1)))
    )
    (if (or (= ventdr 1) (= ventdr 2))
        (progn
            (setq pt2 (POLAR pt1 ang (* 6 sk1)))
            (setq flglen (* 2 sk1))
            (setq piplen (* 1 sk1))
        )
        (if (< ghk 49)
            (progn
                (if (= sd "WAFER")
                    (setq pt2 (POLAR pt1 ang (* 4 sk1)))
                    (setq pt2 (POLAR pt1 ang (* 8 sk1)))
                )
                (setq flglen (* 3 sk1))
                (setq piplen (* 1.5 sk1))
            )
            (progn
                (if (= sd "WAFER")
                    (setq pt2 (POLAR pt1 ang (* 6 sk1)))
                    (setq pt2 (POLAR pt1 ang (* 11 sk1)))
                )
                (setq flglen (* 5 sk1))
                (setq piplen (* 2.5 sk1))
            )
        )
    )
    (initget 1)
    (setq ang1 (GETANGLE pt2 "\nPICK VALVE DIRECTION: "))
    (if (and (<= ang1 (+ ang (dtr 10))) (>= ang1 (- ang (dtr 10))))
        (setq ang1 (GETANGLE pt2 "\nPICK VALVE DIRECTION: "))
    )
    (if (= future 1)
        (command "layer" "s" "2c" "")
        (command "layer" "s" "2h" "")
    )
)

(defun i-while(/ ptw2 ptw3 ptw2a ptw2b)
    (if (or (= ventdr 1) (= ventdr 2))
        (progn
            (setq ptw1 (POLAR pt1 ang (* 3 sk1)))
            (setq ptw2 (POLAR ptw1 ang1 (* 8 sk1)))
            (setq ptw3 (POLAR ptw2 ang1 (* 1.5 sk1)))
            (setq ptw2a(POLAR ptw2 (+ ang (dtr 180)) (* 3 sk1)))
            (setq ptw2b(POLAR ptw2 ang (* 3 sk1)))
        )
        (if (< ghk 49)
            (progn
                (setq ptw1 (POLAR pt1 ang (* 4 sk1)))
                (setq ptw2 (POLAR ptw1 ang1 (* 10 sk1)))
                (setq ptw3 (POLAR ptw2 ang1 (* 1.5 sk1)))
                (setq ptw2a(POLAR ptw2 (+ ang (dtr 180)) (* 3 sk1)))
                (setq ptw2b(POLAR ptw2 ang (* 3 sk1)))
            )
            (progn
                (setq ptw1 (POLAR pt1 ang (* 5.5 sk1)))
                (setq ptw2 (POLAR ptw1 ang1 (* 16 sk1)))
                (setq ptw3 (POLAR ptw2 ang1 (* 2.5 sk1)))
                (setq ptw2a(POLAR ptw2 (+ ang (dtr 180)) (* 5 sk1)))
                (setq ptw2b(POLAR ptw2 ang (* 5 sk1)))
            )
        )
    )
    (if (= future 1)
        (command "layer" "s" "1c" "")
        (command "layer" "s" "1h" "")
    )
    (if (= 1 hand-type)
        (command "pline" (POLAR pt1 ang1 flglen) "w" "0" "0" ptw2 (POLAR pt2 ang1 flglen) "")
        (command "pline" ptw2a "w" "0" "0" ptw1 ptw2b "")
    )
    (command "pline" ptw2  "w" "0" "0" ptw1 "")
    (if (= future 1)
        (command "layer" "s" "5c" "")
        (command "layer" "s" "2h" "")
    )
    (if (= c_item "GAT")
        (command "pline" ptw2  "w" p-wedth2 p-wedth2 ptw3 "")
    )
    (command "pline" ptw2a "w" p-wedth2 p-wedth2 ptw2b "")
)

(defun i-valve1()
    (command "layer" "s" "1c" "")
    (if (and (= con-val nil)(= sd "BW"))
        (progn
            (setq endpoint pt2)
            (command "line" (POLAR pt1 (+ ang (dtr 180)) (* 1.5 sk1)) pt2 "")
            (cond
                ((= future 1)
                    (command "insert" "c:/ghk/iso/isoweld" pt1 sk1 "" "")
                    (command "insert" "c:/ghk/iso/isoweld" pt2 sk1 "" "")
                )
                ((= future 0)
                    (command "layer" "s" "2h" "")
                    (command "circle" pt1 sk1)
                    (command "circle" pt2 sk1)
                )
            )
        )
        (progn
            ;(if (and (or (/= sd "FLG") (/= sd "WAFER")) (= valend-type 2) (= con-val nil))
            (if (or (= sd "BW") (and (= sd "SW") (= valend-type 2) (= con-val nil)))
                (setq endpoint pt2)
                (setq endpoint (POLAR pt2 ang (* 0.75 sk1)))
            )
            (command "line" (POLAR pt1 (+ ang (dtr 180)) (* 1.5 sk1)) (POLAR pt2 ang (* 0.75 sk1)) "")
        )
    )
    (setq endang ang)
    (setq endang1 ang1)
    (setq con-val nil)
)
(defun i-valve2()
    (if (or (and (= con-val nil) (= sd "SW")) (and (= con-val nil)(= sd "SCR'D")))
        (progn
            (command "pline" (POLAR pt1 ang1 flglen) "w" "0" "0" (POLAR (POLAR pt1 (+ ang (dtr 180)) (* 1 sk1)) ang1 flglen) "")
            (command "pline" (POLAR pt1 (+ ang1 (dtr 180)) flglen) "w" "0" "0" (POLAR (POLAR pt1 (+ ang (dtr 180)) (* 1 sk1)) (+ ang1 (dtr 180)) flglen) "")
            (command "pline" (POLAR pt2 ang1 flglen) "w" "0" "0" (POLAR (POLAR pt2 ang (* 1 sk1)) ang1 flglen) "")
            (command "pline" (POLAR pt2 (+ ang1 (dtr 180)) flglen) "w" "0" "0" (POLAR (POLAR pt2 ang (* 1 sk1)) (+ ang1 (dtr 180)) flglen) "")
        )
    )
)
(IF (not i-gas)(load"c:/ghk/iso/fitting"))
(IF (not i-blt)(load"c:/ghk/iso/fitting"))
