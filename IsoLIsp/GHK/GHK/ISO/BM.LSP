(defun bm(/ os st-point snpt2 qty ang sss1 text textlen text8)
    (graphscr)
    (setq os (getvar "osmode"))
    (setvar "cmdecho" 0)
    (setvar "attdia" 0)
    (setq FILE (OPEN "c:/ghk/iso/ISOBM.cfg" "r"))
    (setq bmdist7 (Read-line FILE))
    (setq bmdist8 (Read-line FILE))
    (setq bmdist1 (Read-line FILE))
    (setq bmdist2 (Read-line FILE))
    (setq bmdist3 (Read-line FILE))
    (setq bmdist4 (Read-line FILE))
    (setq bmdist5 (Read-line FILE))
    (setq bmdist6 (Read-line FILE))
    (setq st-point (list (atof bmdist7) (+ (atof bmdist8) 1) 0.0))
    (setq snpt2 (polar st-point (dtr 0) (* 200 s)))
    (setq ang (angle st-point snpt2))
    (setvar "osmode" 0)
    (setq qty 1)
    (setq dwg_no(getvar "dwgname"))
    (if (= (strcase (substr dwg_no (- (strlen dwg_no) 3))) ".DWG")
        (setq dwg_no(substr dwg_no 1 (- (strlen dwg_no) 4)))
    )
    (if (> (strlen (getvar "dwgprefix")) (strlen (getvar "dwgname")))
        (setq dwg_no dwg_no
	      file_no (strcat (getvar "dwgprefix") dwg_no)
        )
        (setq dwg_no(substr (getvar "dwgname") (+ (strlen (getvar "dwgprefix")) 1))
	      file_no (getvar "dwgprefix")
        )
    )
    (c:lst1)
    (while qty
        (selec1)
        (setq st-point (List (car st-point)(- (cadr st-point) (atof bmdist5))))
    )
    (outfile)
    (command "osmode" os)
    (princ)
)
;============ MAIN PROGRAM END ===================

(defun selec1(/ qty1 qty2 qty3 qty4 sss text1 text2 text3 text4 text6
                text7)
 (setq sss(ssget "w" st-point
                     (polar (polar st-point (+ ang (dtr 90)) (atof bmdist5)) ang (atof bmdist1))))
 (if (= sss nil)
    (setq text1 "")
    (setq text1 (cdr (assoc 1 (entget (ssname sss 0)))))
 )
 (setq sss(ssget "w" (polar st-point ang (atof bmdist1))
                     (polar (polar st-point (+ ang (dtr 90)) (atof  bmdist5)) ang (atof bmdist2))))
 (if (= sss nil)
    (setq text2 "")
    (setq text2 (cdr (assoc 1 (entget (ssname sss 0)))))
 )

 (setq sss(ssget "w" (polar st-point ang (atof bmdist2))
                     (polar (polar st-point (+ ang (dtr 90)) (atof bmdist5)) ang (atof bmdist3))))
 (if (= sss nil)
    (setq text3 "")
    (setq text3 (cdr (assoc 1 (entget (ssname sss 0)))))
 )

 (setq sss(ssget "w" (polar st-point ang (atof bmdist3))
                     (polar (polar st-point (+ ang (dtr 90)) (atof bmdist5)) ang (atof bmdist4))))
 (if (= sss nil)
    (setq text4 "")
    (setq text4 (cdr (assoc 1 (entget (ssname sss 0)))))
 )

 (setq sss(ssget "w" (polar st-point ang (atof bmdist4))
                     (polar (polar st-point (+ ang (dtr 90)) (atof bmdist5)) ang (atof bmdist6))))
 (if (= sss nil)
    (setq text5 "")
    (setq text5 (cdr (assoc 1 (entget (ssname sss 0)))))
 )

 (if (and (= text1 "") (= text2 "") (= text3 "") (= text4 "") (= text5 ""))
    (setq qty nil)
    (command "insert" "C:/GHK/ISO/sybm1" (polar st-point (+ ang (dtr 270)) 2)  S "" "" dwg_no text1 text2 text3 text4 text5)
 )
)

(defun outfile(/ n-fnmae op-fname i-qua )
 (graphscr)
 (setq n-fname   (getvar "dwgname")
       n-fname (strcat n-fname ".TXT")
       op-fname(open n-fname "r")
 )
 (setvar "cmdecho" 0)
 (prompt (strcat "\n" (chr 34)n-fname(chr 34) " files maked. \n"))
 (command "attext" "e" (ssget "X" (list (cons 2 "sybm1"))) "" "s" "c:/ghk/iso/sybm.txt" file_no)
 (command "ERASE" (ss-add) "")
 (prompt (strcat "\nThank you for Output File program used. \nType " (chr 34)"OF"(chr 34) " and You can use OF program."))
 (princ)
)
;============ MAIN PROGRAM END ===================
(defun isobm(/ bmbase bmitem bmqty bmsize bmdisc bmnext bmdist1
                 bmdist2 bmdist3 bmdist4 bmdist5 bmdist7 bmdist8 fp)
    (setvar "osmode" 33)
    (setq bmbase (GETPOINT "\n BM List Base & Class Point : "))
    (setq bmitem (GETPOINT bmbase "\n BM Item Point : "))
    (setq bmsize (GETPOINT bmbase "\n BM Size Point : "))
    (setq bmqty  (GETPOINT bmbase "\n BM Q'ty Point : "))
    (setq bmdisc (GETPOINT bmbase "\n BM Disc Point : "))
    (setq bmend  (GETPOINT bmbase "\n BM Chart End Point : "))
    (setq bmnext (GETPOINT bmbase "\n BM List Next Point : "))
    (setvar "osmode" 0)
    (setq bmdist1(- (car bmitem) (car bmbase)))
    (setq bmdist2(- (car bmsize) (car bmbase)))
    (setq bmdist3(- (car bmqty)  (car bmbase)))
    (setq bmdist4(- (car bmdisc) (car bmbase)))
    (setq bmdist6(- (car bmend) (car bmbase)))
    (setq bmdist5(- (cadr bmbase)(cadr bmnext)))
    (setq bmdist7(car bmbase))
    (setq bmdist8(cadr bmbase))
    (setq fp (open "C:/GHK/iso/ISOBM.CFG" "w"))
    (write-line (rtos bmdist7 2 2) fp)
    (write-line (rtos bmdist8 2 2) fp)
    (write-line (rtos bmdist1 2 2) fp)
    (write-line (rtos bmdist2 2 2) fp)
    (write-line (rtos bmdist3 2 2) fp)
    (write-line (rtos bmdist4 2 2) fp)
    (write-line (rtos bmdist5 2 2) fp)
    (write-line (rtos bmdist6 2 2) fp)
    (close fp)
)
