(defun i-flg(/ flglen piplen pt1 pt2 pt3 pt3a pt3b pt3c pt3d pt4 pt4a pt4b
               pt5a pt5b pt6a pt6b pt7 pt7a pt7b pt7c pt7d pt8a pt8b pt8c
               pt9d ang)
    (setiso1)
    (setq c_itemno "060")
    (sc1)
    (flgtypesec)
    (if (= c_disc "")
        (prompt "\nIS NOT SPEC SIZE ")
        (progn
            (i-flg-1)
            (i-flg-2)
        )
    )
    (setiso2)
    (setq old_sd sd)
    (if (/= job_direc1 0)(val-acc))
    (prin1)
)

(defun i-flg-1()
    (if (= job_direc 1)
        (progn
            (setvar "osmode" 1)
            (setq pt1 (GETPOINT "\nPICK START POINT OF SLIP ON FLANGE : "))
            (IF (= pt1 nil)(setq pt1 endpoint))
            (setvar "osmode" 0)
            (setq ang (GETANGLE pt1 "\nPICK 2nd OF SLIP ON FLANGE  DIRECTION: "))
        )
    )
    (setvar "osmode" 0)
    (IF (= pt1 nil)(setq pt1 endpoint))
    (IF (= ang nil)(setq ang endang))
    (if (= sd "LA")
        (setq pt2 (POLAR pt1 ang (* 3.7 sk1)))
        (if (or (= sd "SW") (= sd "SCR'D"))
            (setq pt2 (POLAR pt1 ang (* 0.15 sk1)))
            (setq pt2 (POLAR pt1 ang (* 3 sk1)))
        )
    )
    (initget 1)
    (setq ang1 (GETANGLE pt1 "\nPICK OF SLIP ON FLANGE DIRECTION: "))
    (if (and (<= ang1 (+ ang (dtr 10))) (>= ang1 (- ang (dtr 10))))
        (setq ang1 (GETANGLE pt1 "\nPICK OF SLIP ON FLANGE DIRECTION: "))
    )
)

(defun i-flg-2()
    (ratchan)
    (setq pt3 (POLAR pt2 (+ ang (dtr 180)) flgwidth))
    (setq pt4 (POLAR pt2 ang flgwidth))
    (setq pt3a(POLAR pt3 ang1 flglen))
    (setq pt3b(POLAR pt3 (+ ang1 (dtr 180)) flglen))
    (setq pt3c(POLAR pt3 ang1 piplen))
    (setq pt3d(POLAR pt3 (+ ang1 (dtr 180)) piplen))
    (setq pt4a(POLAR pt4 ang1 flglen))
    (setq pt4b(POLAR pt4 (+ ang1 (dtr 180)) flglen))
    (setq pt5a(POLAR pt4 ang1 (* flglen 0.6)))
    (setq pt5b(POLAR pt4 (+ ang1 (dtr 180)) (* flglen 0.6)))
    (setq pt6a(POLAR pt3 ang1 (* flglen 0.6)))
    (setq pt6b(POLAR pt3 (+ ang1 (dtr 180)) (* flglen 0.6)))
    (setq pt7 (POLAR pt2 (+ ang (dtr 180)) (+ (* flgwidth 2) (* 0.95 sk1))))
    (setq pt7a(POLAR pt7 ang1 flglen))
    (setq pt7b(POLAR pt7 (+ ang1 (dtr 180)) flglen))
    (setq pt7c(POLAR pt7 ang1 piplen))
    (setq pt7d(POLAR pt7 (+ ang1 (dtr 180)) piplen))
    (setq pt8 (POLAR pt2 (+ ang (dtr 180)) (* 0.95 sk1)))
    (setq pt8a(POLAR pt8 ang1 flglen))
    (setq pt8b(POLAR pt8 (+ ang1 (dtr 180)) flglen))
    (setq pt8c(POLAR pt8 ang1 piplen))
    (setq pt8d(POLAR pt8 (+ ang1 (dtr 180)) piplen))
    (if (or (= sd "SW")(= sd "SCR'D"))
        (command "layer" "s" "5c" "")
        (command "layer" "s" "8c" "")
    )
    (cond
        ((= sd "WN")
            (cond
                ((= future 1)
                    (command "solid" pt3c pt1 pt3d "" "")
                    (command "insert" "c:/ghk/iso/isoweld" pt1 sk1 "" "")
                    (if (= dwgtype "D")
                        (command "pline" pt3b "w" "0" "0" pt4b pt3a pt4a "c")
                        (command "solid" pt3b pt4b pt3a pt4a "")
                    )
                    (if (/= dwgtype "D")(bmlist pt3))
                )
                ((= future 0)
                    (command "layer" "s" "2h" "")
                    (command "pline" pt3c "w" "0" "0" pt1 pt3d "")
                    (command "pline" pt3b "w" "0" "0" pt4b pt4a pt3a "c")
                    (command "circle" pt1 sk1)
                )
            )
        )
        ((= sd "SO")
            (cond
                ((= future 1)
                    (command "pline" pt1 "w" p-wedth4 p-wedth4 pt2 "")
                    (if (= dwgtype "D")
                        (command "pline" pt3b "w" "0" "0" pt4b pt3a pt4a "c")
                        (command "solid" pt3b pt4b pt3a pt4a "")
                    )
                    (if (/= dwgtype "D")(bmlist pt3))
                )
                ((= future 0)
                    (command "layer" "s" "2h" "")
                    (command "pline" pt1 "w" "0" "0" pt2 "")
                    (command "pline" pt3b "w" "0" "0" pt4b pt4a pt3a "c")
                )
            )
        )
        ((= sd "LA")
            (cond
                ((= future 1)
                    (command "pline" pt1 "w" p-wedth4 p-wedth4 pt2 "")
                    (if (= dwgtype "D")
                        (progn
                            (command "pline" pt5b "w" "0" "0" pt6b pt5a pt6a "c")
                            (command "pline" pt7b "w" "0" "0" pt8b pt7d pt8d "c")
                            (command "pline" pt7c "w" "0" "0" pt8c pt7a pt8a "c")
                        )
                        (progn
                            (command "solid" pt5b pt6b pt5a pt6a "")
                            (command "solid" pt7b pt8b pt7d pt8d "")
                            (command "solid" pt7c pt8c pt7a pt8a "")
                        )
                    )
                    (command "insert" "c:/ghk/iso/isoweld" pt1 sk1 "" "")
                    (if (/= dwgtype "D")(bmlist pt3))
                    (setq c_item "STE")
                    (setq c_itemno "020")
                    (sc1)
                    (if (/= dwgtype "D")(bmlist pt3))
                )
                ((= future 0)
                    (command "layer" "s" "2h" "")
                    (command "pline" pt1 "w" "0" "0" pt2 "")
                    (command "pline" pt5b "w" "0" "0" pt6b pt6a pt5a "c")
                    (command "pline" pt7b "w" "0" "0" pt8b pt8d pt7d "c")
                    (command "pline" pt7c "w" "0" "0" pt8c pt8a pt7a "c")
                    (command "circle" pt1 sk1)
                )
            )
        )
        ((or (= sd "SW")(= sd "SCR'D"))
            (cond
                ((= future 1)
                    (if (= dwgtype "D")
                        (command "pline" pt3b "w" "0" "0" pt4b pt3a pt4a "c")
                        (command "solid" pt3b pt4b pt3a pt4a "")
                    )
                    (if (/= dwgtype "D")(bmlist pt3))
                )
                ((= future 0)
                    (command "layer" "s" "2h" "")
                    (command "pline" pt3b "w" "0" "0" pt4b pt4a pt3a "c")
                )
            )
        )
    )
    (command "layer" "s" "1c" "")
    (command "line" pt1 (POLAR pt2 ang (* 0.75 sk1)) "")
    (setq endpoint (POLAR pt2 ang (* 0.75 sk1)))
    (setq endang (angle pt1 pt2))
    (setq endang1 ang1)
)

(defun i-flg1(/ flglen piplen pt1 pt2 pt3 pt3a pt3b pt3c pt3d pt4 pt4a pt4b
                pt5a pt5b pt6a pt6b pt7 pt7a pt7b pt7c pt7d pt8a pt8b pt8c
                pt9d ang)
    (setiso1)
    (setq c_itemno "060")
    (sc1)
    (if (= c_disc "")
        (prompt "\nIS NOT SPEC SIZE ")
        (progn
            (if (= job_direc 2)(progn (i-gas)(i-blt)))
            (setq c_itemno "060")
            (sc1)
            (flgtypesec)
            (i-flg1-1)
            (i-flg1-2)
        )
    )
    (setq rat1 nil)
    (setiso2)
    (setq old_sd sd)
    (setq vallast nil)
    (if (or (= sd "SW") (= sd "SCR'D"))(val-acc1)(val-acc2))
    (prin1)
)

(defun i-flg1-1()
    (if (= job_direc 1)
        (progn
            (setvar "osmode" 1)
            (setq pt1 (GETPOINT "\nPICK START POINT OF SLIP ON FLANGE : "))
            (setvar "osmode" 0)
            (IF (= pt1 nil)(setq pt1 endpoint))
            (setq ang (GETANGLE pt1 "\nPICK 2nd OF SLIP ON FLANGE  DIRECTION: "))
        )
    )
    (setvar "osmode" 0)
    (IF (= pt1 nil)(setq pt1 endpoint))
    (IF (= ang nil)(setq ang endang))
    (setq pt1 (POLAR pt1 ang (* 0.75 sk1)))
    (if (= sd "LA")
        (setq pt2 (POLAR pt1 ang (* 3.7 sk1)))
        (if (or (= sd "SW")(= sd "SCR'D"))
            (setq pt2 (POLAR pt1 ang (* 0.15 sk1)))
            (setq pt2 (POLAR pt1 ang (* 3 sk1)))
        )
    )
    (initget 1)
    (setq ang1 (GETANGLE pt1 "\nPICK OF SLIP ON FLANGE DIRECTION: "))
    (if (and (<= ang1 (+ ang (dtr 10))) (>= ang1 (- ang (dtr 10))))
        (setq ang1 (GETANGLE pt1 "\nPICK OF SLIP ON FLANGE DIRECTION: "))
    )
)
(defun i-flg1-2()
    (ratchan)
    (setq pt3 (POLAR pt1 ang flgwidth))
    (setq pt4 (POLAR pt1 (+ ang (dtr 180)) flgwidth))
    (setq pt3a(POLAR pt3 ang1 flglen))
    (setq pt3b(POLAR pt3 (+ ang1 (dtr 180)) flglen))
    (setq pt3c(POLAR pt3 ang1 piplen))
    (setq pt3d(POLAR pt3 (+ ang1 (dtr 180)) piplen))
    (setq pt4a(POLAR pt4 ang1 flglen))
    (setq pt4b(POLAR pt4 (+ ang1 (dtr 180)) flglen))
    (setq pt5a(POLAR pt4 ang1 (* flglen 0.6)))
    (setq pt5b(POLAR pt4 (+ ang1 (dtr 180)) (* flglen 0.6)))
    (setq pt6a(POLAR pt3 ang1 (* flglen 0.6)))
    (setq pt6b(POLAR pt3 (+ ang1 (dtr 180)) (* flglen 0.6)))
    (setq pt7 (POLAR pt1 ang (+ (* flgwidth 2) (* 0.95 sk1))))
    (setq pt7a(POLAR pt7 ang1 flglen))
    (setq pt7b(POLAR pt7 (+ ang1 (dtr 180)) flglen))
    (setq pt7c(POLAR pt7 ang1 piplen))
    (setq pt7d(POLAR pt7 (+ ang1 (dtr 180)) piplen))
    (setq pt8 (POLAR pt1 ang (* 0.95 sk1)))
    (setq pt8a(POLAR pt8 ang1 flglen))
    (setq pt8b(POLAR pt8 (+ ang1 (dtr 180)) flglen))
    (setq pt8c(POLAR pt8 ang1 piplen))
    (setq pt8d(POLAR pt8 (+ ang1 (dtr 180)) piplen))
    (if (or (= sd "SW")(= sd "SCR'D"))
        (command "layer" "s" "5c" "")
        (command "layer" "s" "8c" "")
    )
    (cond
        ((= sd "WN")
            (cond
                ((= future 1)
                    (command "solid" pt3c pt2 pt3d "" "")
                    (if (= dwgtype "D")
                        (command "pline" pt3b "w" "0" "0" pt4b pt3a pt4a "c")
                        (command "solid" pt3b pt4b pt3a pt4a "")
                    )
                    (command "insert" "c:/ghk/iso/isoweld" pt2 sk1 "" "")
                    (if (/= dwgtype "D")(bmlist pt3))
                )
                ((= future 0)
                    (command "layer" "s" "2h" "")
                    (command "pline" pt3c "w" "0" "0" pt2 pt3d "")
                    (command "pline" pt3b "w" "0" "0" pt4b pt4a pt3a "c")
                    (command "circle" pt2 sk1)
                )
            )
        )
        ((= sd "SO")
            (cond
                ((= future 1)
                    (command "pline" pt1 "w" p-wedth4 p-wedth4 pt2 "")
                    (if (= dwgtype "D")
                        (command "pline" pt3b "w" "0" "0" pt4b pt3a pt4a "c")
                        (command "solid" pt3b pt4b pt3a pt4a "")
                    )
                    (if (/= dwgtype "D")(bmlist pt3))
                )
                ((= future 0)
                    (command "layer" "s" "2h" "")
                    (command "pline" pt1 "w" "0" "0" pt2 "")
                    (command "pline" pt3b "w" "0" "0" pt4b pt4a pt3a "c")
                )
            )
        )
        ((= sd "LA")
            (cond
                ((= future 1)
                    (command "pline" pt1 "w" p-wedth4 p-wedth4 pt2 "")
                    (if (= dwgtype "D")
                        (progn
                            (command "pline" pt5b "w" "0" "0" pt6b pt5a pt6a "c")
                            (command "pline" pt7b "w" "0" "0" pt8b pt7d pt8d "c")
                            (command "pline" pt7c "w" "0" "0" pt8c pt7a pt8a "c")
                        )
                        (progn
                            (command "solid" pt5b pt6b pt5a pt6a "")
                            (command "solid" pt7b pt8b pt7d pt8d "")
                            (command "solid" pt7c pt8c pt7a pt8a "")
                        )
                    )
                    (command "insert" "c:/ghk/iso/isoweld" pt2 sk1 "" "")
                    (if (/= dwgtype "D")(bmlist pt3))
                    (setq c_item "STE")
                    (setq c_itemno "020")
                    (sc1)
                    (if (/= dwgtype "D")(bmlist pt3))
                )
                ((= future 0)
                    (command "layer" "s" "2h" "")
                    (command "pline" pt1 "w" "0" "0" pt2 "")
                    (command "pline" pt5b "w" "0" "0" pt6b pt6a pt5a "c")
                    (command "pline" pt7b "w" "0" "0" pt8b pt8d pt7d "c")
                    (command "pline" pt7c "w" "0" "0" pt8c pt8a pt7a "c")
                    (command "circle" pt2 sk1)
                )
            )
        )
        ((or (= sd "SW")(= sd "SCR'D"))
            (cond
                ((= future 1)
                    (if (= dwgtype "D")
                        (command "pline" pt3b "w" "0" "0" pt4b pt3a pt4a "c")
                        (command "solid" pt3b pt4b pt3a pt4a "")
                    )
                    (if (/= dwgtype "D")(bmlist pt3))
                )
                ((= future 0)
                    (command "layer" "s" "2h" "")
                    (command "pline" pt3b "w" "0" "0" pt4b pt4a pt3a "c")
                )
            )
        )
    )
    (command "layer" "s" "1c" "")
    (command "line" pt1 pt2 "")
    (command "line" pt2 (POLAR pt1 (+ ang (dtr 180)) (* 0.75 sk1)) "")
    (setq endpoint pt2)
    (setq endang (angle pt1 pt2))
    (setq endang1 ang1)
)

;;;;blind flange
(defun i-flg2(/ flglen piplen old_ghk pt1 pt2 pt3 pt3a pt3b pt4 pt4a pt4b
                ang)
    (setiso1)
    (setq c_item "BLF")
    (setq c_itemno "060")
    (sc1)
    (set-selec i-flg2-1)
    (setiso2)
    (setq old_sd sd)
    (prin1)
)

(defun i-flg2-1()
    (if (= job_direc 2)(progn (i-gas)(i-blt)))
    (setq c_item "BLF")
    (setq c_itemno "060")
    (sc1)
    (disc-cha sd "BLIND")
    (if (or (= sd "SW")(= sd "SCR'D"))
        (progn
            (setq flglen (* 3 sk1))
            (setq piplen (* 1.5 sk1))
            (setq flgwidth (* 1.25 p-wedth1))
        )
        (progn
            (setq flglen (* 5 sk1))
            (setq piplen (* 2.5 sk1))
            (setq flgwidth (* 1.75 p-wedth1))
        )
    )
    (if (= job_direc 1)
        (progn
            (setvar "osmode" 1)
            (SETQ pt1 (GETPOINT "\nPICK START POINT OF SLIP ON FLANGE : "))
            (setvar "osmode" 0)
            (IF (= pt1 nil)(setq pt1 endpoint))
            (setq ang (GETANGLE pt1 "\nPICK 2nd OF SLIP ON FLANGE  DIRECTION: "))
        )
    )
    (setvar "osmode" 0)
    (IF (= pt1 nil)(setq pt1 endpoint))
    (IF (= ang nil)(setq ang endang))
    (setq pt1 (POLAR pt1 ang (* 0.75 sk1)))
    (setq pt2 (POLAR pt1 ang (* 0.75 sk1)))
    (if (= job_direc 1)
        (progn
            (initget 1)
            (setq ang1 (GETANGLE pt1 "\nPICK OF SLIP ON FLANGE DIRECTION: "))
            (if (and (<= ang1 (+ ang (dtr 10))) (>= ang1 (- ang (dtr 10))))
                (setq ang1 (GETANGLE pt1 "\nPICK OF SLIP ON FLANGE DIRECTION: "))
            )
        )
    )
    (ratchan)
    (setq pt3 (POLAR pt1 (+ ang (dtr 180)) flgwidth))
    (setq pt3a(POLAR pt3 ang1 flglen))
    (setq pt3b(POLAR pt3 (+ ang1 (dtr 180)) flglen))
    (setq pt4 (POLAR pt1 ang flgwidth))
    (setq pt4a(POLAR pt4 ang1 flglen))
    (setq pt4b(POLAR pt4 (+ ang1 (dtr 180)) flglen))
    (if (or (= sd "SW")(= sd "SCR'D"))
        (command "layer" "s" "5c" "")
        (command "layer" "s" "8c" "")
    )
    (cond
        ((= future 1)
            (if (= dwgtype "D")
                (command "pline" pt3b "w" "0" "0" pt4b pt3a pt4a "c")
                (command "solid" pt3b pt4b pt3a pt4a "")
            )
            (if (/= dwgtype "D")(bmlist pt3))
        )
        ((= future 0)
            (command "layer" "s" "2h" "")
            (command "pline" pt3b "w" "0" "0" pt4b pt4a pt3a "c")
        )
    )
    (command "layer" "s" "1c" "")
    (command "line" pt1 pt2 "")
    (setq endpoint pt1)
    (setq endang (angle pt1 pt2))
)
;;;nozzle
(defun i-flg3(/ flglen piplen pt1 pt1a pt1b pt1c pt2 pt3 pt3a pt3b pt3c
                pt3d pt4 pt4a pt4b ang)
    (setiso1)
    (setq c_itemno "060")
    (sc1)
    (flgtypesec)
    (setvar "osmode" 1)
    (SETQ pt1 (GETPOINT "\nPICK START POINT OF SLIP ON FLANGE : "))
    (setvar "osmode" 0)
    (IF (= pt1 nil)(setq pt1 endpoint))
    (setq ang (GETANGLE pt1 "\nPICK 2nd OF SLIP ON FLANGE  DIRECTION: "))
    (IF (= ang nil)(setq ang endang))
    (setq pt2 (POLAR pt1 ang (* 10 sk1)))
    (initget 1)
    (setq ang1 (GETANGLE pt1 "\nPICK OF SLIP ON FLANGE DIRECTION: "))
    (if (and (<= ang1 (+ ang (dtr 10))) (>= ang1 (- ang (dtr 10))))
        (setq ang1 (GETANGLE pt1 "\nPICK OF SLIP ON FLANGE DIRECTION: "))
    )
    (setq pt1c(POLAR pt1 ang flglen))
    (setq pt1a(POLAR pt1c ang1 piplen))
    (setq pt1b(POLAR pt1c (+ ang1 (dtr 180)) piplen))
    (setq pt3 (POLAR pt2 ang (/ piplen 6)))
    (setq pt4 (POLAR pt2 (+ ang (dtr 180)) (/ piplen 2)))
    (setq pt3a(POLAR pt3 ang1 flglen))
    (setq pt3b(POLAR pt3 (+ ang1 (dtr 180)) flglen))
    (setq pt4a(POLAR pt4 ang1 flglen))
    (setq pt4b(POLAR pt4 (+ ang1 (dtr 180)) flglen))
    (setq pt4c(POLAR pt4 ang1 piplen))
    (setq pt4d(POLAR pt4 (+ ang1 (dtr 180)) piplen))
    (cond
        ((= future 1)
            (command "layer" "s" "2c" "")
            (command "pline" pt1b "w" "0" "0" pt4d pt4a pt3a pt3b pt4b pt4c pt1a "")
        )
        ((= future 0)
            (command "layer" "s" "2h" "")
            (command "pline" pt1b "w" "0" "0" pt4d pt4a pt3a pt3b pt4b pt4c pt1a "")
        )
    )
    (command "layer" "s" "1c" "")
    (command "line" pt1 (POLAR pt2 ang (* 0.75 sk1)) "")
    (setq endpoint (POLAR pt2 ang (* 0.75 sk1)))
    (setq endang (angle pt1 pt2))
    (setiso2)
    (if (or (= sd "SW") (= sd "SCR'D"))(val-acc6)(val-acc))
    (setq old_sd sd)
    (prin1)
)

;;;nozzle
(defun i-flg4(/ flglen piplen pt1 pt2a pt2b pt2c pt2 pt3 pt3a pt3b
                pt4 pt4a pt4b pt4c pt4d ang)
    (setiso1)
    (if (and (= job_direc 2) (= future 1))(progn (i-gas)(i-blt)))
    (setq c_itemno "060")
    (sc1)
    (flgtypesec)
    (if (= job_direc 1)
        (progn
            (setvar "osmode" 1)
            (SETQ pt1 (GETPOINT "\nPICK START POINT OF SLIP ON FLANGE : "))
            (setvar "osmode" 0)
            (IF (= pt1 nil)(setq pt1 endpoint))
            (setq ang (GETANGLE pt1 "\nPICK 2nd OF SLIP ON FLANGE  DIRECTION: "))
        )
    )
    (IF (= ang nil)(setq ang endang))
    (IF (= pt1 nil)(setq pt1 endpoint))
    (setq pt1 (POLAR pt1 ang (* 0.75 sk1)))
    (setq pt2 (POLAR pt1 ang (* 10 sk1)))
    (initget 1)
    (setq ang1 (GETANGLE pt1 "\nPICK OF SLIP ON FLANGE DIRECTION: "))
    (if (and (<= ang1 (+ ang (dtr 10))) (>= ang1 (- ang (dtr 10))))
        (setq ang1 (GETANGLE pt1 "\nPICK OF SLIP ON FLANGE DIRECTION: "))
    )
    (setq pt2c(POLAR pt2 (+ ang (dtr 180)) flglen))
    (setq pt2a(POLAR pt2c ang1 piplen))
    (setq pt2b(POLAR pt2c (+ ang1 (dtr 180)) piplen))
    (setq pt3 pt1)
    (setq pt4 (POLAR pt1 ang (/ piplen 6)))
    (setq pt4 (POLAR pt4 ang (/ piplen 2)))
    (setq pt3a(POLAR pt3 ang1 flglen))
    (setq pt3b(POLAR pt3 (+ ang1 (dtr 180)) flglen))
    (setq pt4a(POLAR pt4 ang1 flglen))
    (setq pt4b(POLAR pt4 (+ ang1 (dtr 180)) flglen))
    (setq pt4c(POLAR pt4 ang1 piplen))
    (setq pt4d(POLAR pt4 (+ ang1 (dtr 180)) piplen))
    (cond
        ((= future 1)
            (command "layer" "s" "2c" "")
            (command "pline" pt2b "w" "0" "0" pt4d pt4a pt3a pt3b pt4b pt4c pt2a "")
        )
        ((= future 0)
            (command "layer" "s" "2h" "")
            (command "pline" pt2b "w" "0" "0" pt4d pt4a pt3a pt3b pt4b pt4c pt2a "")
        )
    )
    (command "layer" "s" "1c" "")
    (command "line" (POLAR pt1 (+ ang (dtr 180)) (* 0.5 sk1)) (POLAR pt2 ang (* 1 sk1)) "")
    (setq endpoint pt1)
    (setq endang (angle pt1 pt2))
    (setiso2)
    (setq old_sd sd)
    (prin1)
)

(defun i-flg5(/ flglen piplen pt1 pt2 pt1a pt1b pt1c pt1d)
    (setiso1)
    (setq c_itemno "050")
    (sc1)
    (flgtypesec)
    (setq c_item "SPB")
    (if (= c_disc "")
        (prompt "\nIS NOT SPEC SIZE ")
        (progn
            (i-flg5-1)
        )
    )
    (setiso2)
    (setq old_sd sd)
    (val-acc)
    (prin1)
)

(defun i-flg5-1()
    (if (= job_direc 1)
        (progn
            (setvar "osmode" 1)
            (setq pt1 (GETPOINT "\nPICK START POINT OF SLIP ON FLANGE : "))
            (IF (= pt1 nil)(setq pt1 (POLAR endpoint endang (* 0.75 sk1))))
        )
    )
    (setvar "osmode" 0)
    (IF (= pt1 nil)(setq pt1 (POLAR endpoint endang (* 0.75 sk1))))
    (setq pt2 (POLAR pt1 endang (* 0.75 sk1)))
    (initget 1)
    (setq ang1 (GETANGLE pt1 "\nPICK OF SLIP ON FLANGE DIRECTION: "))
    (if (and (<= ang1 (+ endang (dtr 10))) (>= ang1 (- endang (dtr 10))))
        (setq ang1 (GETANGLE pt1 "\nPICK OF SLIP ON FLANGE DIRECTION: "))
    )
    (setq pt1a(POLAR pt1 ang1 (+ flglen (* 1 sk1))))
    (setq pt1b(POLAR pt1 (+ ang1 (dtr 180)) flglen))
    (setq pt1c(POLAR pt1a ang1 sk1))
    (setq pt1d(POLAR pt1c ang1 (* sk1 2)))
    (ratchan)
    (cond
        ((= future 1)
            (command "layer" "s" "2c" "")
            (command "pline" pt1b "w" p-wedth3 p-wedth3 pt1c "")
            (command "insert" "c:/ghk/iso/isoweld" pt1c sk1 "" "")
            (command "circle" pt1c sk1)
            (command "circle" pt1d sk1)
            (setq c_itemno (strcat c_itemno "1"))
            (if (/= dwgtype "D")(bmlist pt1b))
        )
        ((= future 0)
            (command "layer" "s" "2h" "")
            (command "pline" pt1b "w" "0" "0" pt1c "")
            (command "circle" pt1c sk1)
            (command "circle" pt1d sk1)
        )
    )
    (command "layer" "s" "1c" "")
    (command "line" (POLAR pt1 (+ endang (dtr 180)) (* 0.75 sk1))  pt2 "")
    (setq endpoint pt2)
)

(defun i-flg6(/ flglen piplen pt1 pt2 pt1a pt1b)
    (setiso1)
    (setq c_itemno "060")
    (sc1)
    (flgtypesec)
    (if (= c_disc "")
        (prompt "\nIS NOT SPEC SIZE ")
        (progn
            (setq job_direc1 0)
            (i-flg)
            (setq job_direc1 nil)
            (setq job_direc 2)
            (i-gas)
            (setq old_sd "WAFER")
            (i-flg6-1)
            (IF (not pi-tag)(load"c:/ghk/iso/fitting"))(pi-tag)
            (i-flg1)
        )
    )
    (setiso2)
    (setq old_sd sd)
    (prin1)
)

(defun i-flg6-1()
    (setvar "osmode" 0)
    (IF (= pt1 nil)(setq pt1 (POLAR endpoint endang (* 0.75 sk1))))
    (setq pt2 (POLAR pt1 endang (* 0.75 sk1)))
    (setq ang1 endang1)
    (setq pt1a(POLAR pt1 ang1 piplen))
    (setq pt1b(POLAR pt1 (+ ang1 (dtr 180)) piplen))
    (cond
        ((= future 1)
            (command "layer" "s" "2c" "")
            (command "pline" pt1a "w" p-wedth3 p-wedth3 pt1b "")
        )
        ((= future 0)
            (command "layer" "s" "2h" "")
            (command "pline" pt1a "w" "0" "0" pt1b "")
        )
    )
    (command "layer" "s" "1c" "")
    (command "line" (POLAR pt1 (+ endang (dtr 180)) (* 0.75 sk1))  pt2 "")
    (setq endpoint pt2)
)

(defun flgtypesec()
    (cond
        ((= sd "WN")
            (setq c_item "WNF")
        )
        ((= sd "SO")
            (setq c_item "SOF")
        )
        ((= sd "LA")
            (setq c_item "LJF")
        )
        ((= sd "SW")
            (setq c_item "SWF")
        )
        ((= sd "SCR'D")
            (setq c_item "SCF")
        )
    )
;    (if (or (= sd "SW")(= sd "SCR'D"))
    (if (< ghk 49)
        (progn
            (setq flglen (* 3 sk1))
            (setq piplen (* 1.5 sk1))
            (setq flgwidth (* 1.25 p-wedth1))
        )
        (progn
            (setq flglen (* 5 sk1))
            (setq piplen (* 2.5 sk1))
            (setq flgwidth (* 1.75 p-wedth1))
        )
    )
)
(IF (not i-gas)(load"c:/ghk/iso/fitting"))
(IF (not i-blt)(load"c:/ghk/iso/fitting"))
