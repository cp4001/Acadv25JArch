;Set iso no.1
(defun setiso1()
    (setq olderr *error* *error* ghkerr)
    (setvar "cmdecho" 0)
    (layer1)
    (graphscr)
    (if (= ghk nil)(setq ghk 150))
    (command "layer" "t" "*" "")
    (setq la (getvar "clayer"))
    (setq orth(getvar "orthomode"))
    (setq os(getvar "osmode"))
    (setq c_dwgname "UNNAME")
    (if (= c_class "None")
        (progn
            (c:ssspec)
            (resetiso)
        )
    )
)

(defun setiso2()
    (setq olderr *error* *error* ghkerr)
    (setvar "orthomode" orth)
    (setvar "osmode" os)
    (command "layer" "s" la "")
    (setq sd1 nil)
    (resetiso)
)

(defun set-selec(selec1 /)
        (if (and (= c_disc "") (= con-val nil))
            (prompt "\nIS NOT SPEC SIZE ")
            (selec1)
        )
)


(defun C:DM()
       (IF (not DIMEN)(load"c:/ghk/iso/DIMEN"))
       (setvar "cmdecho" 0)
       (princ " = ISO Demension")
       (DIMEN)
)


(defun C:DM1()
       (IF (not DIMEN1)(load"c:/ghk/iso/DIMEN"))
       (setvar "cmdecho" 0)
       (princ " = ISO Demension")
       (DIMEN1)
)
(defun C:TJ()
       (IF (not TJ)(load"c:/ghk/iso/textang"))
       (setvar "cmdecho" 0)
       (princ " = TEXT JUSTFICATION ")
       (TJ)
)
(defun resetiso()
    (setvar "modemacro" (strcat "Layer:$(substr,$(getvar,clayer),1,8)"
                            " Spec : " (strcat "[" c_class "] ")
                            (if (= ghk nil) " Unselect Size" (strcat " " (rtos ghk 2 0) "A "))
                            " Rat:"(if (= rat "A") " 150#" (if (= rat "B") " 300#" (if (= rat "C") " 600#" (if (= rat "D") " 900#"))))
                            " Flg:"(if (= sd "SO") " SLIP ON" (if (= sd "LA") " LAP JOINT" (if (= sd "WN") " WELD NECK" (if (= sd "SW") " SOCK WELD" (if (= sd "SCR'D") " SCR'D" sd)))))
                            "  " (if (= future 1) " CONT. " (if (= future 0) " HIDDEN "))
                        )
    )
)

;Data file read
(defun sslist1 (file / fn n-line if1)
 (setq lst1 nil lst2 nil)
 (setq fn(open (strcat "c:/ghk/iso/" file".dat") "r"))
 (setq msg(read-line fn))
 (while (setq n-line(read-line fn))
        (setq if1(substr n-line 1 1))
        (cond ((= if1 "*")
               (setq lst1(cons (substr n-line 2) lst1))
              )
              ((= if1 "(")
               (setq lst2(cons (read n-line) lst2))
              )
        )
 )
 (setq lst1(reverse lst1) lst2(reverse lst2))
)

;Data file read
(defun sslist2 (file / fn n-line if1)
 (setq bmlst1 nil bmlst2 nil)
 (setq fn(open (strcat "c:/ghk/iso/" file".spc") "r"))
 (setq msg(read-line fn))
 (while (setq n-line(read-line fn))
        (setq if1(substr n-line 1 1))
        (cond ((= if1 "*")
               (setq bmlst1(cons (read (substr n-line 2)) bmlst1))
              )
              ((= if1 "(")
               (setq bmlst2(cons (read n-line) bmlst2))
              )
        )
 )
 (setq bmlst1(reverse bmlst1) bmlst2(reverse bmlst2))
)
(defun c:ssspec(/ lst1 lst2 lst21 list1 ok)
    (setq dcl_id (load_dialog "c:/ghk/iso/ssspec.dcl"))
    (if (not (new_dialog "ssspec" dcl_id))
        (exit)
    )
    (sslist1 "ssspec")
    (setq   list1 "0")
    (setq   c_class (nth 0 lst1))
    (action_tile "z_list"  "(sub_1 (setq list1 $value))")
    (start_list "z_list")
    (mapcar 'add_list lst1)
    (end_list)
    (setq ok(start_dialog))
    (done_dialog)
    (unload_dialog dcl_id)
    (princ)
)

(defun sub_1(data)
    (setq   c_class (nth (atoi data)   lst1))
    (setq   lst21   (nth (atoi data)   lst2))
    (setq   rat     (nth 0 lst21))
    (setq   rat-txt (nth 1 lst21))
    (sslist2 c_class)
    (setq bmlst1- (nth 0 bmlst1))
    (setq endtype (atof (nth 0 bmlst1-)))
)

(defun ssbolt1(/ lst1 lst2 b-lst1 b-lst2 b-lst20 b-ghk)
    (setq dcl_id (load_dialog "c:/ghk/iso/ssspec.dcl"))
    (if (not (new_dialog "ssbolt" dcl_id))
        (exit)
    )
    (sslist1 "bolt")
    (setq b-ghk (strcat (ch-size ghk) (chr 34)))
    (setq b-lst1(nth (atoi sizenum) lst1))
    (setq b-lst2(nth (atoi sizenum) lst2))
    (if (not lenadd) (setq lenadd "100")  (if (/= lenadd  "100")  (setq lenadd lenadd)))
    (cond
        ((= rat "A")
            (setq b-lst20(nth 0 b-lst2))
        )
        ((= rat "B")
            (setq b-lst20(nth 1 b-lst2))
        )
        ((= rat "C")
            (setq b-lst20(nth 2 b-lst2))
        )
    )
    (setq b-qty(nth 0 b-lst20))
    (setq b-size(nth 1 b-lst20))
    (setq c_itemno "081")
    (sc1)
    (cond
        ((= sd "M")
            (setq b-len(nth 2 b-lst20))
        )
        ((= sd "S")
            (setq b-len(nth 3 b-lst20))
        )
    )
    (action_tile "zghk"    "(setq b-ghk $value)")
    (action_tile "zqty"    "(setq b-qty $value)")
    (action_tile "zsize"   "(setq b-size $value)")
    (action_tile "zlen"    "(setq b-len $value)")
    (action_tile "zlenadd" "(setq lenadd $value)")
    (set_tile "zghk" b-ghk)
    (set_tile "zqty" b-qty)
    (set_tile "zsize" b-size)
    (set_tile "zlen" b-len)
    (set_tile "zlenadd" lenadd)
    (setq ok(start_dialog))
    (done_dialog)
    (unload_dialog dcl_id)
    (princ)
)

(defun ssbolt2(/ lst1 lst2 b-lst1 b-lst2 b-lst20)
    (sslist1 "bolt")
    (setq b-ghk (strcat (ch-size ghk) (chr 34)))
    (setq b-lst1(nth (atoi sizenum) lst1))
    (setq b-lst2(nth (atoi sizenum) lst2))
    (cond
        ((= rat "A")
            (setq b-lst20(nth 0 b-lst2))
        )
        ((= rat "B")
            (setq b-lst20(nth 1 b-lst2))
        )
        ((= rat "C")
            (setq b-lst20(nth 2 b-lst2))
        )
    )
    (setq b-qty(nth 0 b-lst20))
    (setq b-size(nth 1 b-lst20))
    (setq c_itemno "081")
    (sc1)
    (cond
        ((= sd "M")
            (setq b-len(nth 2 b-lst20))
        )
        ((= sd "S")
            (setq b-len(nth 3 b-lst20))
        )
    )
)

(defun sc1(/ bmlst1 bmlst2 bmlst1- i_sock 1_weld i_large bmlst2- bmlst20-
             bmlst21- )
    (sslist2 c_class)
    (setq c_disc "")
    (setq bmlst1- (nth (atoi (substr c_itemno 1 2)) bmlst1))
    (setq i_sock (nth 0 bmlst1-))
    (setq i_weld (nth 1 bmlst1-))
    (setq i_large (nth 2 bmlst1-))
    (setq bmlst2- (nth (atoi (substr c_itemno 1 2)) bmlst2))
    (setq bmlst20- (nth 0 bmlst2-))
    (setq bmlst21- (nth 1 bmlst2-))
    (setq endtype (atoi(nth 0 bmlst1-)))
    (if (and (> ghk 0) (<= ghk (atof i_sock)))
        (setq c_disc (nth 0 bmlst20-))
        (if (and (>= ghk (atof i_sock)) (<= ghk (atof i_weld)))
            (setq c_disc (nth 1 bmlst20-))
            (if (and (>= ghk (atof i_weld)) (<= ghk (atof i_large)))
                (setq c_disc (nth 2 bmlst20-))
            )
        )
    )
    (if (and (> ghk 0) (<= ghk (atof i_sock)))
        (setq sd (nth 0 bmlst21-))
        (if (and (>= ghk (atof i_sock)) (<= ghk (atof i_weld)))
            (setq sd (nth 1 bmlst21-))
            (if (and (>= ghk (atof i_weld)) (<= ghk (atof i_large)))
                (setq sd (nth 2 bmlst21-))
            )
        )
    )
)
(defun ftof()
 (setq dcl_id (load_dialog "c:/ghk/iso/ssspec.dcl"))
  (if (not (new_dialog "ftof" dcl_id))
      (exit)
  )
 (sslist1 "fitting")
 (cond
    ((= "100" t-sizeno)
        (setq ftofnum "0")
    )
    ((= "125" t-sizeno)
        (setq ftofnum "1")
    )
    ((= "150" t-sizeno)
        (setq ftofnum "2")
    )
    ((= "200" t-sizeno)
        (setq ftofnum "3")
    )
    ((= "250" t-sizeno)
        (setq ftofnum "4")
    )
    ((= "300" t-sizeno)
        (setq ftofnum "5")
    )
    ((= "350" t-sizeno)
        (setq ftofnum "6")
    )
    ((= "400" t-sizeno)
        (setq ftofnum "7")
    )
    ((= "450" t-sizeno)
        (setq ftofnum "8")
    )
    ((= "500" t-sizeno)
        (setq ftofnum "9")
    )
 )
 (setq pipe-size (nth (atoi ftofnum) lst1))
 (setq lst2- (nth (atoi ftofnum) lst2))
 (setq fitlen n-len)
 (setq ell90(nth 0 lst2-))
 (setq ell90q "0")
 (setq ell90s(nth 1 lst2-))
 (setq ell90sq "0")
 (setq ell45(nth 2 lst2-))
 (setq ell45q "0")
 (setq lentee(nth 3 lst2-))
 (setq lenteeq "0")
 (setq lenred(nth 4 lst2-))
 (setq lenredq "0")
 (action_tile "zpipe-size" "(setq pipe-size $value)")
 (action_tile "mainsize"   "(ftof_1 (setq ftofnum $value))")
 (action_tile "zfitlen"    "(setq fitlen $value)")
 (action_tile "zell90"     "(setq ell90 $value)")
 (action_tile "zell90q"    "(setq ell90q $value)")
 (action_tile "zell90s"    "(setq ell90s $value)")
 (action_tile "zell90sq"   "(setq ell90sq $value)")
 (action_tile "zell45"     "(setq ell45 $value)")
 (action_tile "zell45q"    "(setq ell45q $value)")
 (action_tile "zlentee"    "(setq lentee $value)")
 (action_tile "zlenteeq"   "(setq lenteeq $value)")
 (action_tile "zlenred"    "(setq lenred $value)")
 (action_tile "zlenredq"   "(setq lenredq $value)")
 (start_list "mainsize")
 (mapcar 'add_list lst1)
 (end_list)
 (set_tile "mainsize" ftofnum)
 (set_tile "zpipe-size" pipe-size)
 (set_tile "zfitlen"  fitlen)
 (set_tile "zell90"   ell90)
 (set_tile "zell90q"  ell90q)
 (set_tile "zell90s"  ell90s)
 (set_tile "zell90sq" ell90sq)
 (set_tile "zell45"   ell45)
 (set_tile "zell45q"  ell45q)
 (set_tile "zlentee"  lentee)
 (set_tile "zlenteeq" lenteeq)
 (set_tile "zlenred"  lenred)
 (set_tile "zlenredq" lenredq)
 (setq ok(start_dialog))
 (done_dialog)
 (unload_dialog dcl_id)
 (if (= ok 1)(ftof_2))
 (princ)
)

(defun ftof_1(data)
    (setq pipe-size (nth (atoi data) lst1))
    (setq lst2- (nth (atoi data) lst2))
    (setq ell90(nth 0 lst2-))
    (setq ell90s(nth 1 lst2-))
    (setq ell45(nth 2 lst2-))
    (setq lentee(nth 3 lst2-))
    (setq lenred(nth 4 lst2-))
    (set_tile "zpipe-size" pipe-size)
    (set_tile "zfitlen"  fitlen)
    (set_tile "zell90"   ell90)
    (set_tile "zell90q"  ell90q)
    (set_tile "zell90s"  ell90s)
    (set_tile "zell90sq" ell90sq)
    (set_tile "zell45"   ell45)
    (set_tile "zell45q"  ell45q)
    (set_tile "zlentee"  lentee)
    (set_tile "zlenteeq" lenteeq)
    (set_tile "zlenred"  lenred)
    (set_tile "zlenredq" lenredq)
)

(defun ftof_2()
    (setq n-len(rtos (- (atoi fitlen) (+
                    (* (atoi ell90)  (atoi ell90q))
                    (* (atoi ell90s) (atoi ell90sq))
                    (* (atoi ell45)  (atoi ell45q))
                    (* (atoi lentee) (atoi lenteeq))
                    (* (atoi lenred) (atoi lenredq))
                )) 2 0)
    )
)

(defun ssbolt3()
    (setq b-len(+ (atof b-len) (atof lenadd)))
    (cond
        ((< b-len 53)
            (setq b-len "50")
        )
        ((< b-len 58)
            (setq b-len "55")
        )
        ((< b-len 63)
            (setq b-len "60")
        )
        ((< b-len 68)
            (setq b-len "65")
        )
        ((< b-len 73)
            (setq b-len "70")
        )
        ((< b-len 78)
            (setq b-len "75")
        )
        ((< b-len 83)
            (setq b-len "80")
        )
        ((< b-len 88)
            (setq b-len "85")
        )
        ((< b-len 93)
            (setq b-len "90")
        )
        ((< b-len 98)
            (setq b-len "95")
        )
        ((< b-len 103)
            (setq b-len "100")
        )
        ((< b-len 108)
            (setq b-len "105")
        )
        ((< b-len 113)
            (setq b-len "110")
        )
        ((< b-len 118)
            (setq b-len "115")
        )
        ((< b-len 123)
            (setq b-len "120")
        )
        ((< b-len 128)
            (setq b-len "125")
        )
        ((< b-len 133)
            (setq b-len "130")
        )
        ((< b-len 138)
            (setq b-len "135")
        )
        ((< b-len 143)
            (setq b-len "140")
        )
        ((< b-len 148)
            (setq b-len "145")
        )
        ((< b-len 153)
            (setq b-len "150")
        )
        ((< b-len 158)
            (setq b-len "155")
        )
        ((< b-len 163)
            (setq b-len "160")
        )
        ((< b-len 168)
            (setq b-len "165")
        )
        ((< b-len 173)
            (setq b-len "170")
        )
        ((< b-len 178)
            (setq b-len "175")
        )
        ((< b-len 183)
            (setq b-len "180")
        )
        ((< b-len 188)
            (setq b-len "185")
        )
        ((< b-len 193)
            (setq b-len "190")
        )
        ((< b-len 198)
            (setq b-len "195")
        )
        ((< b-len 203)
            (setq b-len "200")
        )
        ((< b-len 208)
            (setq b-len "205")
        )
        ((< b-len 213)
            (setq b-len "210")
        )
        ((< b-len 218)
            (setq b-len "215")
        )
        ((< b-len 223)
            (setq b-len "220")
        )
        ((< b-len 228)
            (setq b-len "225")
        )
        ((< b-len 233)
            (setq b-len "230")
        )
        ((< b-len 238)
            (setq b-len "235")
        )
        ((< b-len 243)
            (setq b-len "240")
        )
        ((< b-len 248)
            (setq b-len "245")
        )
        ((< b-len 253)
            (setq b-len "250")
        )
        ((< b-len 258)
            (setq b-len "255")
        )
        ((< b-len 263)
            (setq b-len "260")
        )
        ((< b-len 268)
            (setq b-len "265")
        )
        ((< b-len 273)
            (setq b-len "270")
        )
        ((< b-len 278)
            (setq b-len "275")
        )
        ((< b-len 283)
            (setq b-len "280")
        )
        ((< b-len 288)
            (setq b-len "285")
        )
        ((< b-len 293)
            (setq b-len "290")
        )
        ((< b-len 298)
            (setq b-len "295")
        )
        ((< b-len 303)
            (setq b-len "300")
        )
        ((< b-len 308)
            (setq b-len "305")
        )
    )
)

(defun isomenuset()
    (setq dcl_id (load_dialog "c:/ghk/iso/valist.dcl"))
    (if (not old_point)(setq old_point '(640 480)))
    (if (not (new_dialog "menuset" dcl_id "" old_point))
        (exit)
    )
    (start_image "image1")
    (slide_image 0 0 (dimx_tile "image1") (dimy_tile "image1") "con-type")
    (end_image)
    (start_image "image2")
    (slide_image 0 0 (dimx_tile "image2") (dimy_tile "image2") "handwhil")
    (end_image)
    (start_image "image3")
    (slide_image 0 0 (dimx_tile "image3") (dimy_tile "image3") "txt-stl")
    (end_image)
    (start_image "image4")
    (slide_image 0 0 (dimx_tile "image4") (dimy_tile "image4") "valend")
    (end_image)
    (cond ((= 1 con-type) (set_tile "zcon1" "1"))
          ((= 2 con-type) (set_tile "zcon2" "1"))
    )
    (cond ((= 1 hand-type) (set_tile "zhand1" "1"))
          ((= 2 hand-type) (set_tile "zhand2" "1"))
    )
    (cond ((= 1 size-type) (set_tile "zsize1" "1"))
          ((= 2 size-type) (set_tile "zsize2" "1"))
    )
    (cond ((= 1 valend-type) (set_tile "zvalend1" "1"))
          ((= 2 valend-type) (set_tile "zvalend2" "1"))
    )
    (cond ((= 1 text-type) (set_tile "ztext1" "1"))
          ((= 2 text-type) (set_tile "ztext2" "1"))
    )
    (pset-s1)
    (action_tile "accept" "(progn (setq x $x y $y) (setq old_point (done_dialog 1)))")
    (action_tile "ansicode" "(setq ansi- 1 ks- 0)(pset-s1)")
    (action_tile "kscode"   "(setq ansi- 0 ks- 1)(pset-s1)")
    (action_tile "zhand1" "(setq hand-type 1)")
    (action_tile "zhand2" "(setq hand-type 2)")
    (action_tile "zsize1" "(setq size-type 1)")
    (action_tile "zsize2" "(setq size-type 2)")
    (action_tile "zcon1" "(setq con-type 1)")
    (action_tile "zcon2" "(setq con-type 2)")
    (action_tile "ztext1" "(setq text-type 1)")
    (action_tile "ztext2" "(setq text-type 2)")
    (action_tile "zvalend1" "(setq valend-type 1)")
    (action_tile "zvalend2" "(setq valend-type 2)")
    (setq ok(start_dialog))
    (done_dialog)
    (unload_dialog dcl_id)
    (princ)
)

(defun pset-s1()
 (if (= 1 ks-)
      (set_tile "kscode" "1")
      (set_tile "ansicode" "1")
 )
)

(defun control(/ wlist)
    (setq dcl_id (load_dialog "c:/ghk/iso/valist.dcl"))
    (if (not old_point)(setq old_point '(640 480)))
    (if (not (new_dialog "valist" dcl_id "" old_point))
        (exit)
    )
    (setq wlist
        (list  "    Gate VA"
               "    Glove VA"
               "    Check VA"
               "     Ball VA"
               "    Butter VA"
               "     Dia. VA"
               "    Needle VA"
               "     3 WAY VA"
        )
    )
    (if (not num1)(setq num1 "0"))
    (setq con-val 1)
    (cond ((= 1 future) (set_tile "zfuture1" "1"))
          ((= 0 future) (set_tile "zfuture2" "1"))
    )
    (action_tile "accept" "(progn (setq x $x y $y) (setq old_point (done_dialog 1)))")
    (action_tile "itemlist" "(control- (setq num1 $value))")
    (action_tile "zfuture1" "(setq future 1)(setq p-wedth1 (* 0.2 sk1))(setq p-wedth2 (* 0.3 sk1))(setq p-wedth3 (* 0.5 sk1))(setq p-wedth4 (* 0.7 sk1))")
    (action_tile "zfuture2" "(setq future 0)(setq p-wedth1 (* 0 sk1))(setq p-wedth2 (* 0 sk1))(setq p-wedth3 (* 0 sk1))(setq p-wedth4 (* 0 sk1))")
    (start_list "itemlist")
    (mapcar 'add_list wlist)
    (end_list)
    (set_tile "itemlist" num1)
    (setq ok(start_dialog))
    (done_dialog)
    (unload_dialog dcl_id)
    (if (= ok 1)(control-1))
    (princ)
)

(defun control-(data)
    (setq vasel1 (+ (atoi data) 1))
)

(defun control-1()
    (setq job_direc 2)
    (if (= vasel1 nil)(setq vasel1 1))
    (if (= future 1)
        (if (= vasel1 5)
            (prompt " IS NOT SPEC SIZE ")
            (progn
                (IF (not i-blt)(load"c:/ghk/iso/fitting"))
                (i-blt)
            )
        )
    )
    (cond
        ((= vasel1 1)
            (IF (NOT i-gate)(load"c:/ghk/iso/i-valve"))(i-gate)
        )
        ((= vasel1 2)
            (IF (NOT i-glov)(load"c:/ghk/iso/i-valve"))(i-glov)
        )
        ((= vasel1 3)
            (IF (NOT i-che)(load"c:/ghk/iso/i-valve"))(i-che)
        )
        ((= vasel1 4)
            (IF (NOT i-ball)(load"c:/ghk/iso/i-valve"))(i-ball)
        )
        ((= vasel1 5)
            (IF (NOT i-but)(load"c:/ghk/iso/i-valve"))(i-but)
        )
        ((= vasel1 6)
            (IF (NOT i-dia)(load"c:/ghk/iso/i-valve"))(i-dia)
        )
        ((= vasel1 7)
            (IF (NOT i-ndl)(load"c:/ghk/iso/i-valve"))(i-ndl)
        )
        ((= vasel1 8)
            (IF (NOT i-thway)(load"c:/ghk/iso/i-valve"))(i-thway)
        )
    )
)

(defun val-acc(/ wlist)
    (setq dcl_id (load_dialog "c:/ghk/iso/valist.dcl"))
    (if (not old_point)(setq old_point '(640 480)))
    (if (not (new_dialog "valist" dcl_id "" old_point))
        (exit)
    )
    (setq wlist
        (list  "    Gate VA"
               "    Glove VA"
               "    End Flange"
               "   Blind Flange"
               "    Check VA"
               "     Ball VA"
               "    Butter VA"
               "     Dia. VA"
               "    Safety VA"
               "    Control VA"
               "    Y-Straner"
               "    B-Straner"
               "    T-Straner"
               "       Trap"
               "    Spectacle"
               "    Needle VA"
               "     3 WAY VA"
        )
    )
    (if (not num2)(setq num2 "0"))
    (cond ((= 1 future) (set_tile "zfuture1" "1"))
          ((= 0 future) (set_tile "zfuture2" "1"))
    )
    (action_tile "accept" "(progn (setq x $x y $y) (setq old_point (done_dialog 1)))")
    (action_tile "itemlist" "(valacc- (setq num2 $value))")
    (action_tile "zfuture1" "(setq future 1)(setq p-wedth1 (* 0.2 sk1))(setq p-wedth2 (* 0.3 sk1))(setq p-wedth3 (* 0.5 sk1))(setq p-wedth4 (* 0.7 sk1))")
    (action_tile "zfuture2" "(setq future 0)(setq p-wedth1 (* 0 sk1))(setq p-wedth2 (* 0 sk1))(setq p-wedth3 (* 0 sk1))(setq p-wedth4 (* 0 sk1))")
    (start_list "itemlist")
    (mapcar 'add_list wlist)
    (end_list)
    (set_tile "itemlist" num2)
    (setq ok(start_dialog))
    (done_dialog)
    (unload_dialog dcl_id)
    (if (= ok 1)(valacc-1))
    (princ)
)

(defun valacc-(data)
    (setq vasel1 (+ (atoi data) 1))
)

(defun valacc-1()
    (setq job_direc 2)
    (if (= vasel1 nil)(setq vasel1 1))
    (if (= future 1)
        (progn
            (IF (not i-gas)(load"fitting"))(i-gas)
            (if (or (= vasel1 7) (= vasel1 15) (= vasel1 9) (= vasel1 10))
                (prompt "  ")
                (progn
                    (IF (not i-blt)(load"fitting"))(i-blt)
                )
            )
        )
    )
    (cond
        ((= vasel1 1)
            (IF (NOT i-gate)(load"c:/ghk/iso/i-valve"))(i-gate)
        )
        ((= vasel1 2)
            (IF (NOT i-glov)(load"c:/ghk/iso/i-valve"))(i-glov)
        )
        ((= vasel1 3)
            (IF (NOT i-flg1)(load"c:/ghk/iso/i-flg"))(i-flg1)
        )
        ((= vasel1 4)
            (IF (NOT i-flg2)(load"c:/ghk/iso/i-flg"))(i-flg2)
        )
        ((= vasel1 5)
            (IF (NOT i-che)(load"c:/ghk/iso/i-valve"))(i-che)
        )
        ((= vasel1 6)
            (IF (NOT i-ball)(load"c:/ghk/iso/i-valve"))(i-ball)
        )
        ((= vasel1 7)
            (IF (NOT i-but)(load"c:/ghk/iso/i-valve"))(i-but)
        )
        ((= vasel1 8)
            (IF (NOT i-dia)(load"c:/ghk/iso/i-valve"))(i-dia)
        )
        ((= vasel1 9)
            (IF (NOT i-safety)(load"c:/ghk/iso/i-valve"))(i-safety)
        )
        ((= vasel1 10)
            (control)
        )
        ((= vasel1 11)
            (IF (NOT i-ystr)(load"c:/ghk/iso/i-str"))(i-ystr)
        )
        ((= vasel1 12)
            (IF (NOT i-bstr)(load"c:/ghk/iso/i-str"))(i-bstr)
        )
        ((= vasel1 13)
            (IF (NOT i-tstr)(load"c:/ghk/iso/i-str"))(i-tstr)
        )
        ((= vasel1 14)
            (IF (NOT i-trap)(load"c:/ghk/iso/i-str"))(i-trap)
        )
        ((= vasel1 15)
            (IF (NOT i-flg5)(load"c:/ghk/iso/i-flg"))(i-flg5)
        )
        ((= vasel1 16)
            (IF (NOT i-ndl)(load"c:/ghk/iso/i-valve"))(i-ndl)
        )
        ((= vasel1 17)
            (IF (NOT i-thway)(load"c:/ghk/iso/i-valve"))(i-thway)
        )
    )
)

(defun val-acc1(/ wlist);;male
    (setq dcl_id (load_dialog "c:/ghk/iso/valist.dcl"))
    (if (not old_point)(setq old_point '(640 480)))
    (if (not (new_dialog "valist" dcl_id "" old_point))
        (exit)
    )
    (setq wlist
        (list   "     PIPE"
                "     PLUG"
                "    CON.RED Large End    "
                "    CON.RED Small End    "
                "    ECC.RED Large End    "
                "    ECC.RED Small End    "
                "     Gate VA    "
                "    Glove VA    "
                "    End Flange"
                "   Blind Flange"
                "  Vent & Drain  "
                "     PI valve   "
                "      Nipple    "
        )
    )
    (if (not num3)(setq num3 "0"))
    (cond ((= 1 future) (set_tile "zfuture1" "1"))
          ((= 0 future) (set_tile "zfuture2" "1"))
    )
    (action_tile "accept" "(progn (setq x $x y $y) (setq old_point (done_dialog 1)))")
    (action_tile "itemlist" "(valacc1- (setq num3 $value))")
    (action_tile "zfuture1" "(setq future 1)(setq p-wedth1 (* 0.2 sk1))(setq p-wedth2 (* 0.3 sk1))(setq p-wedth3 (* 0.5 sk1))(setq p-wedth4 (* 0.7 sk1))")
    (action_tile "zfuture2" "(setq future 0)(setq p-wedth1 (* 0 sk1))(setq p-wedth2 (* 0 sk1))(setq p-wedth3 (* 0 sk1))(setq p-wedth4 (* 0 sk1))")
    (start_list "itemlist")
    (mapcar 'add_list wlist)
    (end_list)
    (set_tile "itemlist" num3)
    (setq ok(start_dialog))
    (done_dialog)
    (unload_dialog dcl_id)
    (if (= ok 1)(valacc1-1))
    (princ)
)

(defun valacc1-(data)
    (setq fttsel1 (+ (atoi data) 1))
)

(defun valacc1-1()
   (setq job_direc 2)
    (if (= fttsel1 nil)(setq fttsel1 1))
   (cond
       ((= fttsel1 1)
           (IF (not i-pipe)(load"c:/ghk/iso/i-pipe"))(i-pipe)
       )
       ((= fttsel1 2)
           (IF (not i-plg)(load"c:/ghk/iso/fitting"))(i-plg)
       )
       ((= fttsel1 3)
            (IF (not i-swg1)(load"c:/ghk/iso/i-red"))(setq swg-type 1)(i-swg1)
       )
       ((= fttsel1 4)
            (IF (not i-swg2)(load"c:/ghk/iso/i-red"))(setq swg-type 2)(i-swg2)
       )
       ((= fttsel1 5)
            (IF (not i-swg1)(load"c:/ghk/iso/i-red"))(setq swg-type 3)(i-swg1)
       )
       ((= fttsel1 6)
            (IF (not i-swg2)(load"c:/ghk/iso/i-red"))(setq swg-type 4)(i-swg2)
       )
       ((= fttsel1 7)
            (IF (NOT i-gate)(load"c:/ghk/iso/i-valve"))(i-gate)
       )
       ((= fttsel1 8)
            (IF (NOT i-glov)(load"c:/ghk/iso/i-valve"))(i-glov)
       )
       ((= fttsel1 9)
            (if (= future 1)
                (progn
                    (IF (not i-gas)(load"c:/ghk/iso/fitting"))(i-gas)
                    (IF (not i-blt)(load"c:/ghk/iso/fitting"))(i-blt)
                )
            )
            (IF (NOT i-flg1)(load"c:/ghk/iso/i-flg"))(i-flg1)
       )
       ((= fttsel1 10)
            (if (= future 1)
                (progn
                    (IF (not i-gas)(load"c:/ghk/iso/fitting"))(i-gas)
                    (IF (not i-blt)(load"c:/ghk/iso/fitting"))(i-blt)
                )
            )
            (IF (NOT i-flg2)(load"c:/ghk/iso/i-flg"))(i-flg2)
       )
        ((= fttsel1 11)
            (val-acc4)
        )
        ((= fttsel1 12)
            (val-acc5)
        )
        ((= fttsel1 13)
            (IF (not i-nip)(load"c:/ghk/iso/fitting"))(i-nip)
        )
   )
)

(defun val-acc2(/ wlist)
    (setq dcl_id (load_dialog "c:/ghk/iso/valist.dcl"))
    (if (not old_point)(setq old_point '(640 480)))
    (if (not (new_dialog "valist" dcl_id "" old_point))
        (exit)
    )
    (setq wlist
        (list   "       PIPE"
                "     90ELBOW"
                "     45ELBOW"
                "   TEE Straight      "
                "    TEE Brenct       "
                " Red TEE Straight    "
                "  Red TEE Brenct     "
                "CON.RED Large End    "
                "CON.RED Small End    "
                "ECC.RED Large End    "
                "ECC.RED Small End    "
                "  Start Flange"
                "  Vent & Drain  "
                "     PI valve   "
                "  Nipple    "
        )
    )
    (if (not num4)(setq num4 "0"))
    (cond ((= 1 future) (set_tile "zfuture1" "1"))
          ((= 0 future) (set_tile "zfuture2" "1"))
    )
    (action_tile "accept" "(progn (setq x $x y $y) (setq old_point (done_dialog 1)))")
    (action_tile "itemlist" "(valacc2- (setq num4 $value))")
    (action_tile "zfuture1" "(setq future 1)(setq p-wedth1 (* 0.2 sk1))(setq p-wedth2 (* 0.3 sk1))(setq p-wedth3 (* 0.5 sk1))(setq p-wedth4 (* 0.7 sk1))")
    (action_tile "zfuture2" "(setq future 0)(setq p-wedth1 (* 0 sk1))(setq p-wedth2 (* 0 sk1))(setq p-wedth3 (* 0 sk1))(setq p-wedth4 (* 0 sk1))")
    (start_list "itemlist")
    (mapcar 'add_list wlist)
    (end_list)
    (set_tile "itemlist" num4)
    (setq ok(start_dialog))
    (done_dialog)
    (unload_dialog dcl_id)
    (if (= ok 1)(valacc2-1))
    (princ)
)
(defun valacc2-(data)
    (setq fttsel2 (+ (atoi data) 1))
)

(defun valacc2-1()
    (setq job_direc 2)
    (if (= fttsel2 nil)(setq fttsel2 1))
    (cond
        ((= fttsel2 1)
            (IF (not i-pipe)(load"c:/ghk/iso/i-pipe"))(i-pipe)
        )
        ((= fttsel2 2)
            (IF (not i-90elbow)(load"c:/ghk/iso/i-elbow"))(setq v-point 1)(i-90elbow)
        )
        ((= fttsel2 3)
            (IF (not i-45elbow)(load"c:/ghk/iso/i-elbow"))(setq v-point 1)(i-45elbow)
        )
        ((= fttsel2 4)
            (IF (not i-tee1)(load"c:/ghk/iso/i-tee"))(i-tee1)
        )
        ((= fttsel2 5)
            (IF (not i-tee2)(load"c:/ghk/iso/i-tee"))(i-tee2)
        )
        ((= fttsel2 6)
            (IF (not i-tee3)(load"c:/ghk/iso/i-tee"))(i-tee3)
        )
        ((= fttsel2 7)
            (IF (not i-tee4)(load"c:/ghk/iso/i-tee"))(i-tee4)
        )
        ((= fttsel2 8)
            (IF (not i-swg1)(load"c:/ghk/iso/i-red"))(setq swg-type 1)(i-swg1)
        )
        ((= fttsel2 9)
            (IF (not i-swg2)(load"c:/ghk/iso/i-red"))(setq swg-type 2)(i-swg2)
        )
        ((= fttsel2 10)
            (IF (not i-swg1)(load"c:/ghk/iso/i-red"))(setq swg-type 3)(i-swg1)
        )
        ((= fttsel2 11)
            (IF (not i-swg2)(load"c:/ghk/iso/i-red"))(setq swg-type 4)(i-swg2)
        )
        ((= fttsel2 12)
            (IF (NOT i-flg)(load"c:/ghk/iso/i-flg"))(i-flg)
        )
        ((= fttsel2 13)
            (val-acc4)
        )
        ((= fttsel2 14)
            (val-acc5)
        )
        ((= fttsel2 15)
            (IF (not i-nip)(load"c:/ghk/iso/fitting"))(i-nip)
        )
    )
)

(defun val-acc3(/ wlist);;female
    (setq dcl_id (load_dialog "c:/ghk/iso/valist.dcl"))
    (if (not old_point)(setq old_point '(640 480)))
    (if (not (new_dialog "valist" dcl_id "" old_point))
        (exit)
    )
    (setq wlist
        (list   "    90ELBOW     "
                "    45ELBOW     "
                "  TEE Straight  "
                "   TEE Brenct   "
                "Red TEE Straight"
                " Red TEE Brenct "
                "     Union      "
                "    Full Coup.  "
                "       Cap      "
                "     Gate VA    "
                "    Glove VA    "
                "    Steam Trap  "
                "   Start Flange "
                "   Vent & Drain "
                "     PI valve   "
        )
    )
    (if (not num5)(setq num5 "0"))
    (cond ((= 1 future) (set_tile "zfuture1" "1"))
          ((= 0 future) (set_tile "zfuture2" "1"))
    )
    (action_tile "accept" "(progn (setq x $x y $y) (setq old_point (done_dialog 1)))")
    (action_tile "itemlist" "(valacc3- (setq num5 $value))")
    (action_tile "zfuture1" "(setq future 1)(setq p-wedth1 (* 0.2 sk1))(setq p-wedth2 (* 0.3 sk1))(setq p-wedth3 (* 0.5 sk1))(setq p-wedth4 (* 0.7 sk1))")
    (action_tile "zfuture2" "(setq future 0)(setq p-wedth1 (* 0 sk1))(setq p-wedth2 (* 0 sk1))(setq p-wedth3 (* 0 sk1))(setq p-wedth4 (* 0 sk1))")
    (start_list "itemlist")
    (mapcar 'add_list wlist)
    (end_list)
    (set_tile "itemlist" num5)
    (setq ok(start_dialog))
    (done_dialog)
    (unload_dialog dcl_id)
    (if (= ok 1)(valacc3-1))
    (princ)
)
(defun valacc3-(data)
    (setq fttsel3 (+ (atoi data) 1))
)

(defun valacc3-1()
    (setq job_direc 2)
    (if (= fttsel3 nil)(setq fttsel3 1))
    (cond
        ((= fttsel3 1)
            (IF (not i-90elbow)(load"c:/ghk/iso/i-elbow"))(setq v-point 1)(i-90elbow)
        )
        ((= fttsel3 2)
            (IF (not i-45elbow)(load"c:/ghk/iso/i-elbow"))(setq v-point 1)(i-45elbow)
        )
        ((= fttsel3 3)
            (IF (not i-tee1)(load"c:/ghk/iso/i-tee"))(i-tee1)
        )
        ((= fttsel3 4)
            (IF (not i-tee2)(load"c:/ghk/iso/i-tee"))(i-tee2)
        )
        ((= fttsel3 5)
            (IF (not i-tee3)(load"c:/ghk/iso/i-tee"))(i-tee3)
        )
        ((= fttsel3 6)
            (IF (not i-tee4)(load"c:/ghk/iso/i-tee"))(i-tee4)
        )
        ((= fttsel3 7)
            (IF (not i-uni)(load"c:/ghk/iso/fitting"))(i-uni)
        )
        ((= fttsel3 8)
            (IF (not i-fcp)(load"c:/ghk/iso/fitting"))(i-fcp)
        )
        ((= fttsel3 9)
            (IF (not i-cap)(load"c:/ghk/iso/fitting"))(i-cap)
        )
        ((= fttsel3 10)
            (IF (NOT i-gate)(load"c:/ghk/iso/i-valve"))(i-gate)
        )
        ((= fttsel3 11)
            (IF (NOT i-glov)(load"c:/ghk/iso/i-valve"))(i-glov)
        )
        ((= fttsel3 12)
            (IF (NOT i-trap)(load"c:/ghk/iso/i-str"))(i-trap)
        )
        ((= fttsel3 13)
            (IF (NOT i-flg)(load"c:/ghk/iso/i-flg"))(i-flg)
        )
        ((= fttsel3 14)
            (val-acc4)
        )
        ((= fttsel3 15)
            (val-acc5)
        )
    )
)

(defun val-acc4(/ wlist);;VENT & DRAIN
    (setq dcl_id (load_dialog "c:/ghk/iso/valist.dcl"))
    (if (not old_point)(setq old_point '(640 480)))
    (if (not (new_dialog "valist" dcl_id "" old_point))
        (exit)
    )
    (setq wlist
        (list   "     Gate VA    "
                "    Glove VA    "
        )
    )
    (if (not num6)(setq num6 "0"))
    (cond ((= 1 future) (set_tile "zfuture1" "1"))
          ((= 0 future) (set_tile "zfuture2" "1"))
    )
    (action_tile "accept" "(progn (setq x $x y $y) (setq old_point (done_dialog 1)))")
    (action_tile "itemlist" "(valacc4- (setq num6 $value))")
    (action_tile "zfuture1" "(setq future 1)(setq p-wedth1 (* 0.2 sk1))(setq p-wedth2 (* 0.3 sk1))(setq p-wedth3 (* 0.5 sk1))(setq p-wedth4 (* 0.7 sk1))")
    (action_tile "zfuture2" "(setq future 0)(setq p-wedth1 (* 0 sk1))(setq p-wedth2 (* 0 sk1))(setq p-wedth3 (* 0 sk1))(setq p-wedth4 (* 0 sk1))")
    (start_list "itemlist")
    (mapcar 'add_list wlist)
    (end_list)
    (set_tile "itemlist" num6)
    (setq ok(start_dialog))
    (done_dialog)
    (unload_dialog dcl_id)
    (if (= ok 1)(valacc4-1))
    (princ)
)
(defun valacc4-(data)
    (setq fttsel4 (+ (atoi data) 1))
)

(defun valacc4-1()
    (setq job_direc 2)
    (if (= fttsel4 nil)(setq fttsel4 1))
    (setq ventdr 1)
    (cond
        ((= fttsel4 1)
            (setq c_itemno "090")
            (sc1)
            (if (<= ghk endtype)
                (progn
                    (IF (NOT i-gate)(load"c:/ghk/iso/i-valve"))(i-gate)
                    (IF (not i-nip)(load"c:/ghk/iso/fitting"))(i-nip)
                    (IF (not i-cap)(load"c:/ghk/iso/fitting"))(i-cap)
                )
                (prompt "\nIS NOT SPEC SIZE ")
            )
        )
        ((= fttsel4 2)
            (setq c_itemno "100")
            (sc1)
            (if (<= ghk endtype)
                (progn
                    (IF (NOT i-glov)(load"c:/ghk/iso/i-valve"))(i-glov)
                    (IF (not i-nip)(load"c:/ghk/iso/fitting"))(i-nip)
                    (IF (not i-cap)(load"c:/ghk/iso/fitting"))(i-cap)
                )
                (prompt "\nIS NOT SPEC SIZE ")
            )
        )
    )
)

(defun val-acc5(/ wlist);;PI GAGE
    (setq dcl_id (load_dialog "c:/ghk/iso/valist.dcl"))
    (if (not old_point)(setq old_point '(640 480)))
    (if (not (new_dialog "valist" dcl_id "" old_point))
        (exit)
    )
    (setq wlist
        (list   "     Gate VA    "
                "    Glove VA    "
        )
    )
    (if (not num7)(setq num7 "0"))
    (cond ((= 1 future) (set_tile "zfuture1" "1"))
          ((= 0 future) (set_tile "zfuture2" "1"))
    )
    (action_tile "accept" "(progn (setq x $x y $y) (setq old_point (done_dialog 1)))")
    (action_tile "itemlist" "(valacc5- (setq num7 $value))")
    (action_tile "zfuture1" "(setq future 1)(setq p-wedth1 (* 0.2 sk1))(setq p-wedth2 (* 0.3 sk1))(setq p-wedth3 (* 0.5 sk1))(setq p-wedth4 (* 0.7 sk1))")
    (action_tile "zfuture2" "(setq future 0)(setq p-wedth1 (* 0 sk1))(setq p-wedth2 (* 0 sk1))(setq p-wedth3 (* 0 sk1))(setq p-wedth4 (* 0 sk1))")
    (start_list "itemlist")
    (mapcar 'add_list wlist)
    (end_list)
    (set_tile "itemlist" num7)
    (setq ok(start_dialog))
    (done_dialog)
    (unload_dialog dcl_id)
    (if (= ok 1)(valacc5-1))
    (princ)
)
(defun valacc5-(data)
    (setq fttsel5 (+ (atoi data) 1))
)

(defun valacc5-1()
    (setq job_direc 2)
    (if (= fttsel5 nil)(setq fttsel5 1))
    (setq ventdr 2)
    (cond
        ((= fttsel5 1)
            (setq c_itemno "090")
            (sc1)
            (IF (NOT i-gate)(load"c:/ghk/iso/i-valve"))
            (if (<= ghk endtype)
                (i-gate)
                (prompt "\nIS NOT SPEC SIZE ")
            )
        )
        ((= fttsel5 2)
            (setq c_itemno "100")
            (sc1)
            (IF (NOT i-glov)(load"c:/ghk/iso/i-valve"))
            (if (<= ghk endtype)
                (i-glov)
                (prompt "\nIS NOT SPEC SIZE ")
            )
        )
    )
    (setq ventdr nil)
)

(defun val-acc6(/ wlist)
    (setq dcl_id (load_dialog "c:/ghk/iso/valist.dcl"))
    (if (not old_point)(setq old_point '(640 480)))
    (if (not (new_dialog "valist" dcl_id "" old_point))
        (exit)
    )
    (setq wlist
        (list  "    End Flange"
               "   Blind Flange"
               "    Control VA"
        )
    )
    (if (not num8)(setq num8 "0"))
    (cond ((= 1 future) (set_tile "zfuture1" "1"))
          ((= 0 future) (set_tile "zfuture2" "1"))
    )
    (action_tile "accept" "(progn (setq x $x y $y) (setq old_point (done_dialog 1)))")
    (action_tile "itemlist" "(valacc6- (setq num8 $value))")
    (action_tile "zfuture1" "(setq future 1)(setq p-wedth1 (* 0.2 sk1))(setq p-wedth2 (* 0.3 sk1))(setq p-wedth3 (* 0.5 sk1))(setq p-wedth4 (* 0.7 sk1))")
    (action_tile "zfuture2" "(setq future 0)(setq p-wedth1 (* 0 sk1))(setq p-wedth2 (* 0 sk1))(setq p-wedth3 (* 0 sk1))(setq p-wedth4 (* 0 sk1))")
    (start_list "itemlist")
    (mapcar 'add_list wlist)
    (end_list)
    (set_tile "itemlist" num8)
    (setq ok(start_dialog))
    (done_dialog)
    (unload_dialog dcl_id)
    (if (= ok 1)(valacc6-1))
    (princ)
)

(defun valacc6-(data)
    (setq vasel1 (+ (atoi data) 1))
)

(defun valacc6-1()
    (setq job_direc 2)
    (if (= fttsel6 nil)(setq fttsel6 1))
    (if (= future 1)
        (progn
            (IF (not i-gas)(load"c:/ghk/iso/fitting"))(i-gas)
            (IF (not i-blt)(load"c:/ghk/iso/fitting"))(i-blt)
        )
    )
    (cond
        ((= vasel1 1)
            (IF (NOT i-flg1)(load"c:/ghk/iso/i-flg"))(i-flg1)
        )
        ((= vasel1 2)
            (IF (NOT i-flg2)(load"c:/ghk/iso/i-flg"))(i-flg2)
        )
        ((= vasel1 3)
            (control)
        )
    )
)

(defun disc-cha(ch1 ch2 / qty1 qty2 text1 text2 text3)
    (setq qty1 1)
    (setq qty2 1)
    (while qty1
        (setq text1 (substr c_disc qty2 (strlen ch1)))
        (if (= ch1 text1)
            (progn
               (setq text2 (substr c_disc 1 (- qty2 1)))
               (setq text3 (substr c_disc (+ qty2 (strlen ch1))))
               (setq c_disc (strcat text2 ch2 text3))
               (setq qty1 nil)
            )
            (setq qty2 (+ qty2 1))
        )
    )
)

(defun ratchan()
    (if (/= rat1 nil)
        (cond
            ((= rat1 "A")
                (setq c_item (strcat c_item "1"))
                (disc-cha rat-txt "150#")
            )
            ((= rat1 "B")
                (setq c_item (strcat c_item "3"))
                (disc-cha rat-txt "300#")
            )
            ((= rat1 "C")
                (setq c_item (strcat c_item "6"))
                (disc-cha rat-txt "600#")
            )
            ((= rat1 "D")
                (setq c_item (strcat c_item "9"))
                (disc-cha rat-txt "900#")
            )
            ((= rat1 "E")
                (setq c_item (strcat c_item "15"))
                (disc-cha rat-txt "1500#")
            )
        )
    )
)
(setq s (getvar "dimscale"))
(setq sk1 (* 0.7 s))
(setq txt-h 2.5)
(setq p-wedth1 (* 0 sk1))
(setq p-wedth2 (* 0 sk1))
(setq p-wedth3 (* 0 sk1))
(setq p-wedth4 (* 0 sk1))
(setq dwgtype "D")
(if (not rat)(setq rat "A"))
(if (not sd)(setq sd "SO"))
(if (not future)(setq future 1))
(if (not smalls)(setq smalls 50))
(if (not c_class)(setq c_class "None"))
(if (not c_item)(setq c_item "None"))
(if (not con-type)(setq con-type 2))
(if (not hand-type)(setq hand-type 2))
(if (not size-type)(setq size-type 2))
(if (not valend-type)(setq valend-type 2))
(if (not text-type)(setq text-type 2))
(if (not ghk)(setq ghk 150))
(load"c:/ghk/iso/IM")
