(defun c:im(/ x y a b)
        (defun ccmmdd(menuit)
               (if (= menuit "Mview")
                         (if (= (getvar "tilemode") 1) (setvar "tilemode" 0))
               )
               (command menuit)
               (princ "\r                                                                              ")
               (prompt "\rCommand: ")
               (princ (strcase menuit))
        )
        (setq x 0 y 0)
        (setq dcl_id (load_dialog "im.dcl"))
        (if (not old_point_start)(setq old_point_start '(640 480)))
        (new_dialog "sld" dcl_id "" old_point_start)
        (start_image "s_m")
        (setq b (dimy_tile "s_m"))
        (setq a (fix (* b 1.3874)))
        (fill_image 3 3 a b 252)
        (fill_image 0 0 (- a 3) (- b 3) 8)
        (slide_image 0 0 (- a 3) (- b 3) "c:/ghk/iso/im")
        (end_image)
        (action_tile "s_m" "(progn (setq x $x y $y) (setq old_point_start (done_dialog 0)))")
        (start_dialog)
        (unload_dialog dcl_id)
        (setq x (/ x (/ (- a 3) 12.4866)))
        (setq y (/ y (/ (- b 3) 9.0)))
        (if (and (< x 12.4866)(< y 9)(> x 0)(> y 0))
                (cond ((< y 1.125)(cond ((< x 1.5608)(IF (not p-cal1)(load"c:/ghk/iso/TEXTANG"))(c:p-cal1)(c:im))
                                        ((< x 3.1217)(IF (not p-cal2)(load"c:/ghk/iso/TEXTANG"))(c:p-cal2)(c:im))
                                        ((< x 4.6825)(IF (not p-cal3)(load"c:/ghk/iso/TEXTANG"))(c:p-cal3)(c:im))
                                        ((< x 6.2433)(IF (not p-cal4)(load"c:/ghk/iso/TEXTANG"))(c:p-cal4)(c:im))
                                        ((< x 7.8041)(IF (not p-cal5)(load"c:/ghk/iso/TEXTANG"))(c:p-cal5)(c:im))
                                        ((< x 9.3649)(val-acc4)(c:im))
                                        ((< x 10.9258)(IF(not import)(load"c:/ghk/iso/import"))(c:import)(c:im))
                                        ((< x 12.4866)(command "SNAPSTYL" "1")(c:im))
                                   )
                      )
                      ((< y 2.25)(cond ((< x 1.5608)(menucmd "s=X")(menucmd "s=linesize"))
                                        ((< x 3.1217)(menucmd "s=X")(menucmd "s=linesize"))
                                        ((< x 4.6825)(IF (not i-sec)(load"c:/ghk/iso/fitting"))(i-sec)(c:im))
                                        ((< x 6.2433)(IF (not i-flow)(load"c:/ghk/iso/fitting"))(i-flow)(c:im))
                                        ((< x 7.8041)(IF (not i-wol)(load"c:/ghk/iso/fitting"))(setq job_direc 1)(i-wol)(c:im))
                                        ((< x 9.3649)(IF (not i-uni)(load"c:/ghk/iso/fitting"))(setq job_direc 1)(i-uni)(c:im))
                                        ((< x 10.9258))
                                        ((< x 12.4866)(command "SNAPSTYL" "0"))
                                  )
                      )
                      ((< y 3.375)(cond ((< x 1.5608)(c:ssspec)(resetiso)(c:im))
                                        ((< x 3.1217)(setq future 1)(setq p-wedth1 (* 0.2 sk1))(setq p-wedth2 (* 0.3 sk1))(setq p-wedth3 (* 0.5 sk1))(setq p-wedth4 (* 0.7 sk1))(resetiso)(c:im))
                                        ((< x 4.6825)(setq future 0)(setq p-wedth1 (* 0 sk1))(setq p-wedth2 (* 0 sk1))(setq p-wedth3 (* 0 sk1))(setq p-wedth4 (* 0 sk1))(resetiso)(c:im))
                                        ((< x 6.2433)(command "zoom" "d" pause pause pause)(c:im))
                                        ((< x 7.8041)(command "zoom" "w" pause pause)(c:im))
                                        ((< x 9.3649)(if (not i-ystr)(load"c:/ghk/iso/i-str"))(setq job_direc 1)(i-ystr)(c:im))
                                        ((< x 10.9258)(if (not i-thway)(load"c:/ghk/iso/i-valve"))(setq job_direc 1)(i-thway)(c:im))
                                        ((< x 12.4866)(IF (not i-chs)(load"c:/ghk/iso/textang"))(i-chs)(c:im))
                                   )
                      )
                      ((< y 4.5)(cond ((< x 1.5608)  (IF (NOT i-gate)(load"c:/ghk/iso/i-valve"))(setq job_direc 1)(i-gate)(c:im))
                                        ((< x 3.1217)(IF (NOT i-glov)(load"c:/ghk/iso/i-valve"))(setq job_direc 1)(i-glov)(c:im))
                                        ((< x 4.6825)(IF (NOT i-che)(load"c:/ghk/iso/i-valve"))(setq job_direc 1)(i-che)(c:im))
                                        ((< x 6.2433)(IF (NOT i-ball)(load"c:/ghk/iso/i-valve"))(setq job_direc 1)(i-ball)(c:im))
                                        ((< x 7.8041)(IF (NOT i-but)(load"c:/ghk/iso/i-valve"))(setq job_direc 1)(i-but)(c:im))
                                        ((< x 9.3649)(IF (NOT i-dia)(load"c:/ghk/iso/i-valve"))(setq job_direc 1)(i-dia)(c:im))
                                        ((< x 10.9258)(IF (NOT i-safety)(load"c:/ghk/iso/i-valve"))(setq job_direc 1)(i-safety)(c:im))
                                        ((< x 12.4866)(if (not i-ndl)(load"c:/ghk/iso/i-valve"))(setq job_direc 1)(i-ndl)(c:im))
                                 )
                      )
                      ((< y 5.625)(cond ((< x 1.5608)(IF (not i-fcp)(load"c:/ghk/iso/fitting"))(setq job_direc 1)(i-fcp)(c:im))
                                        ((< x 3.1217)(IF (not i-swg1)(load"c:/ghk/iso/i-red"))(setq job_direc 1)(setq swg-type 3)(i-swg1))
                                        ((< x 4.6825)(IF (not i-swg2)(load"c:/ghk/iso/i-red"))(setq job_direc 1)(setq swg-type 4)(i-swg2))
                                        ((< x 6.2433)(IF (not i-trap)(load"c:/ghk/iso/i-str"))(setq job_direc 1)(i-trap)(c:im))
                                        ((< x 7.8041)(IF (not i-flg5)(load"c:/ghk/iso/i-flg"))(setq job_direc 1)(i-flg5)(c:im))
                                        ((< x 9.3649)(IF (not i-flg3)(load"c:/ghk/iso/i-flg"))(setq job_direc 1)(i-flg3)(c:im))
                                        ((< x 10.9258)(IF (not i-flg4)(load"c:/ghk/iso/i-flg"))(setq job_direc 1)(i-flg4)(c:im))
                                        ((< x 12.4866)(IF (not i-tee4)(load"c:/ghk/iso/i-tee"))(setq job_direc 1)(i-tee4))
                                  )
                      )
                      ((< y 6.75)(cond ((< x 1.5608)(IF (not i-hcp)(load"c:/ghk/iso/fitting"))(setq job_direc 1)(i-hcp)(c:im))
                                       ((< x 3.1217)(IF (not i-swg1)(load"c:/ghk/iso/i-red"))(setq job_direc 1)(setq swg-type 1)(i-swg1))
                                       ((< x 4.6825)(IF (not i-swg2)(load"c:/ghk/iso/i-red"))(setq job_direc 1)(setq swg-type 2)(i-swg2))
                                       ((< x 6.2433)(IF (not i-flg6)(load"c:/ghk/iso/i-flg"))(setq job_direc 1)(i-flg6)(c:im))
                                       ((< x 7.8041))
                                       ((< x 9.3649)(IF (not i-flg2)(load"c:/ghk/iso/i-flg"))(setq job_direc 1)(i-flg2)(c:im))
                                      ((< x 10.9258)(IF (not i-flg2)(load"c:/ghk/iso/i-flg"))(setq job_direc 1)(i-flg2)(c:im))
                                      ((< x 12.4866)(IF (not i-tee3)(load"c:/ghk/iso/i-tee"))(setq job_direc 1)(i-tee3))
                                  )
                      )
                      ((< y 7.875)(cond ((< x 1.5608)(IF (not i-cap)(load"c:/ghk/iso/fitting"))(setq job_direc 1)(i-cap)(c:im))
                                        ((< x 3.1217)(IF (not i-gas)(load"c:/ghk/iso/fitting"))(setq job_direc 1)(i-gas)(c:im))
                                        ((< x 4.6825)(IF (not i-blt)(load"c:/ghk/iso/fitting"))(setq job_direc 1)(i-blt)(c:im))
                                        ((< x 6.2433)(IF (not i-45elbow)(load"c:/ghk/iso/i-elbow"))(setq job_direc 1)(setq v-point 1)(i-45elbow)(c:im))
                                        ((< x 7.8041)(IF (not i-45elbow)(load"c:/ghk/iso/i-elbow"))(setq job_direc 1)(setq v-point 1)(i-45elbow)(c:im))
                                        ((< x 9.3649)(IF (not i-flg1)(load"c:/ghk/iso/i-flg"))(setq job_direc 1)(i-flg1)(c:im))
                                       ((< x 10.9258)(IF (not i-flg1)(load"c:/ghk/iso/i-flg"))(setq job_direc 1)(i-flg1)(c:im))
                                       ((< x 12.4866)(IF (not i-tee2)(load"c:/ghk/iso/i-tee"))(setq job_direc 1)(i-tee2)(c:im))
                                  )
                      )
                      ((< y 9)(cond ((< x 1.5608)(IF (not dimen)(load"c:/ghk/iso/dimen"))(dimen)(c:im))
                                    ((< x 3.1217)(IF (not i-pipe)(load"c:/ghk/iso/i-pipe"))(setq job_direc 1)(i-pipe)(c:im))
                                    ((< x 4.6825)(IF (not i-pipe)(load"c:/ghk/iso/i-pipe"))(setq job_direc 1)(i-pipe)(c:im))
                                    ((< x 6.2433)(IF (not i-90elbow)(load"c:/ghk/iso/i-elbow"))(setq job_direc 1)(setq v-point 1)(i-90elbow)(c:im))
                                    ((< x 7.8041)(IF (not i-90elbow)(load"c:/ghk/iso/i-elbow"))(setq job_direc 1)(setq v-point 1)(i-90elbow)(c:im))
                                    ((< x 9.3649)(IF (not i-flg)(load"c:/ghk/iso/i-flg"))(setq job_direc 1)(i-flg)(c:im))
                                   ((< x 10.9258)(IF (not i-flg)(load"c:/ghk/iso/i-flg"))(setq job_direc 1)(i-flg)(c:im))
                                   ((< x 12.4866)(IF (not i-tee1)(load"c:/ghk/iso/i-tee"))(setq job_direc 1)(i-tee1)(c:im))
                                )
                      )
                );cond close
        );if close
        (princ)
        )
