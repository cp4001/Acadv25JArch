(defun i-wol(/ sd pt1 pt0 pt2 ang ang1 pt1a pt1b pt3 pt3a pt3b pt4 pt4a
               pt4b ghk1 br-size1 br-size2)
    (setiso1)
    (ch-size ghk)
    (if (> ghk endtype)
        (progn
            (i-wol2)
            (setq ghk1 ghk)
            (setq ghk br-size1)
            (setq c_itemno "010")
            (sc1)
            (cond
                ((= sd "SCR'D")
                    (setq c_item "TOL")
                )
                ((= sd "SW")
                    (setq c_item "SOL")
                )
                ((= sd "BW")
                    (setq c_item "WOL")
                )
            )
            (setq ghk ghk1)
            (i-wol1)
        )
    )
    (setiso2)
    (val-acc1)
    (prin1)
)

(defun i-wol1()
    (if (= c_disc "")
        (prompt " IS NOT SPEC SIZE ")
        (progn
            (setvar "osmode" 512)
            (ftt-base c_item)
            (setq pt2 (POLAR pt0 ang (* 3 sk1)))
            (command "layer" "s" "5c" "")
            (setq pt1a (POLAR pt1  ang1 (* 1 sk1)))
            (setq pt1b (POLAR pt1  (+ ang1 (dtr 180)) (* 1 sk1)))
            (setq pt3  (POLAR pt1  ang (* 2 sk1)))
            (setq pt3a (POLAR pt3  ang1 (* 1.5 sk1)))
            (setq pt3b (POLAR pt3  (+ ang1 (dtr 180)) (* 1.5 sk1)))
            (setq pt4  (POLAR pt3  ang (* 1.5 sk1)))
            (setq pt4a (POLAR pt4  ang1 (* 1 sk1)))
            (setq pt4b (POLAR pt4  (+ ang1 (dtr 180)) (* 1 sk1)))
            (cond
                ((= future 1)
                    (setq c_itemno (strcat c_itemno "4"))
                    (if (/= dwgtype "D")
                        (if (= size-type 1)
                            (bmlist1 pt1b (strcat (ch-size ghk) (chr 34) "x" br-size2 (chr 34)))
                            (bmlist1 pt1b (strcat (rtos ghk 2 0) "Ax" (rtos br-size1 2 0) "A"))
                        )
                    )
                    (command "layer" "s" "5c" "")
                )
                ((= future 0)
                    (command "layer" "s" "2h" "")
                )
            )
            (command "pline" pt1a "w" (if (= future 0) "0" p-wedth1) (if (= future 0) "0" p-wedth1) pt3a pt4a pt4b pt3b pt1b "")
            (command "pline" pt3a "w" (if (= future 0) "0" p-wedth1) (if (= future 0) "0" p-wedth1) pt3b "")
            (command "layer" "s" "1c" "")
            (command "line" pt1 pt2 "")
            (setq endpoint pt2)
            (setq endang (angle pt0 pt2))
        )
    )
)

(defun i-fcp(/ sd pt1 pt0 pt2 ang ang1 pt1a pt1b pt1c pt1d
                pt1e pt1f pt1g pt1h)
    (setiso1)
    (setq c_itemno "020")
    (sc1)
    (cond
        ((/= sd1 nil)
            (if (= sd1 "SCR'D")
                (setq c_item "CPLT")
                (setq c_item "CPL")
            )
            (disc-cha sd sd1)
        )
        ((= sd1 nil)
            (setq c_item "CPL")
        )
    )
    (if (= c_disc "")
        (prompt " IS NOT SPEC SIZE ")
        (progn
            (setvar "osmode" 1)
            (ftt-base "COUPLING")
;            (setq pt2 (POLAR pt0 ang 1))
            (setq pt2 pt0)
            (setq pt1a (POLAR pt1  ang1 (* 1.5 sk1)))
            (setq pt1b (POLAR pt1a ang (* 1 sk1)))
            (setq pt1c (POLAR pt1b ang (* 1 sk1)))
            (setq pt1d (POLAR pt1c ang (* 1 sk1)))
            (setq pt1e (POLAR pt1a (+ ang1 (dtr 180)) (* 3 sk1)))
            (setq pt1f (POLAR pt1e ang (* 1 sk1)))
            (setq pt1g (POLAR pt1f ang (* 1 sk1)))
            (setq pt1h (POLAR pt1g ang (* 1 sk1)))
            (cond
                ((= future 1)
                    (if (/= dwgtype "D")(bmlist pt1b))
                    (command "layer" "s" "3c" "")
                )
                ((= future 0)
                    (command "layer" "s" "2h" "")
                )
            )
            (command "pline" pt1a "w" (if (= future 0) "0" p-wedth1) (if (= future 0) "0" p-wedth1) pt1c pt1g pt1e  "c")
;            (command "pline" pt1a "w" p-wedth1 p-wedth1 pt1c pt1g pt1e "")
;            (command "pline" pt1d "w" p-wedth1 p-wedth1 pt1b pt1f pt1h "")
            (command "layer" "s" "1c" "")
            (command "line" pt1 pt2 "")
            (setq endpoint pt2)
            (setq endang (angle pt1 pt2))
        )
    )
    (setiso2)
    (val-acc1)
    (prin1)
)

(defun i-uni(/ sd pt1 pt0 pt2 ang ang1 pt1a pt1b pt3 pt3a
                pt3b pt4 pt4a pt4b)
    (setiso1)
    (setq c_itemno "020")
    (sc1)
    (cond
        ((/= sd1 nil)
            (if (= sd1 "SCR'D")
                (setq c_item "UNIT")
                (setq c_item "UNI")
            )
            (disc-cha sd sd1)
        )
        ((= sd1 nil)
            (setq c_item "UNI")
        )
    )
    (if (= c_disc "")
        (prompt " IS NOT SPEC SIZE ")
        (progn
            (setvar "osmode" 1)
            (ftt-base "UNION")
            (setq pt2 pt0)
            (setq pt1a (POLAR pt1  ang1 (* 1.5 sk1)))
            (setq pt1b (POLAR pt1 (+ ang1 (dtr 180)) (* 1.5 sk1)))
            (setq pt3  (POLAR pt1 ang (* 1 sk1)))
            (setq pt3a (POLAR pt3  ang1 (* 3 sk1)))
            (setq pt3b (POLAR pt3 (+ ang1 (dtr 180)) (* 3 sk1)))
            (setq pt4  (POLAR pt3 ang (* 1 sk1)))
            (setq pt4a (POLAR pt4  ang1 (* 1.5 sk1)))
            (setq pt4b (POLAR pt4 (+ ang1 (dtr 180)) (* 1.5 sk1)))
            (cond
                ((= future 1)
                    (if (/= dwgtype "D")(bmlist pt1b))
                    (command "layer" "s" "3c" "")
                )
                ((= future 0)
                    (command "layer" "s" "2h" "")
                )
            )
            (command "pline" pt1a "w" (if (= future 0) "0" p-wedth1) (if (= future 0) "0" p-wedth1) pt1b "")
            (command "pline" pt3a "w" (if (= future 0) "0" p-wedth1) (if (= future 0) "0" p-wedth1) pt3b "")
            (command "pline" pt4a "w" (if (= future 0) "0" p-wedth1) (if (= future 0) "0" p-wedth1) pt4b "")
            (command "layer" "s" "1c" "")
            (command "line" pt1 pt2 "")
            (setq endpoint pt2)
            (setq endang (angle pt0 pt2))
        )
    )
    (setiso2)
    (val-acc1)
    (prin1)
)

(defun i-hcp(/ sd pt1 pt0 pt2 ang ang1 pt1a pt1b pt1c pt1d
                pt1e pt1f)
    (setiso1)
    (setq c_itemno "020")
    (sc1)
    (cond
        ((/= sd1 nil)
            (if (= sd1 "SCR'D")
                (setq c_item "HCPT")
                (setq c_item "HCP")
            )
            (disc-cha sd sd1)
        )
        ((= sd1 nil)
            (setq c_item "HCP")
        )
    )
    (if (= c_disc "")
        (prompt " IS NOT SPEC SIZE ")
        (progn
            (setvar "osmode" 512)
            (ftt-base "HALF COUPLING")
            (setq pt2 (POLAR pt0 ang (* 1 sk1)))
            (setq pt1a (POLAR pt1 (+ ang1 (dtr 180)) (* 1.5 sk1)))
            (setq pt1b (POLAR pt1a ang (* 2 sk1)))
            (setq pt1c (POLAR pt1b ang (* 1 sk1)))
            (setq pt1d (POLAR pt1  ang1 (* 1.5 sk1)))
            (setq pt1e (POLAR pt1d ang (* 2 sk1)))
            (setq pt1f (POLAR pt1e ang (* 1 sk1)))
            (cond
                ((= future 1)
                    (if (/= dwgtype "D")(bmlist pt1b))
                    (command "layer" "s" "3c" "")
                )
                ((= future 0)
                    (command "layer" "s" "2h" "")
                )
            )
            (command "pline" pt1a "w" (if (= future 0) "0" p-wedth1) (if (= future 0) "0" p-wedth1) pt1c pt1f pt1d "")
;            (command "pline" pt1a "w" p-wedth1 p-wedth1 pt1b pt1e pt1d "")
;            (command "pline" pt1c "w" p-wedth1 p-wedth1 pt1b pt1e pt1f "")
            (command "layer" "s" "1c" "")
            (command "line" pt1 pt2 "")
            (setq endpoint pt2)
            (setq endang (angle pt0 pt2))
        )
    )
    (setiso2)
    (val-acc1)
    (prin1)
)

(defun i-cap(/ sd pt1 pt0 pt2 ang ang1 pt1a pt1b pt1c pt1d pt1e)
    (setiso1)
    (setq c_itemno "010")
    (sc1)
    (cond
        ((/= sd1 nil)
            (if (= sd1 "SCR'D")
                (setq c_item "CAPT")
                (setq c_item "CAP")
            )
            (disc-cha sd sd1)
        )
        ((= sd1 nil)
            (if (= ventdr 1)
                (if (/= sd "SCR'D")
                    (progn
                        (disc-cha sd "SCR'D")
                        (setq sd "SCR'D")
                        (setq c_item "CAPT")
                    )
                    (setq c_item "CAP")
                )
                (setq c_item "CAP")
            )
        )
    )
    (set-selec i-cap1)
    (setq ventdr nil)
    (setiso2)
    (prin1)
)

(defun i-cap1()
    (setvar "osmode" 1)
    (ftt-base "CAP")
    (if (<= ghk endtype)
        (setq caplen (* 3 sk1))
        (setq caplen (* 9 sk1))
    )
    (setq pt2 (POLAR pt1 ang (* caplen 0.666)))
    (setq pt1a (POLAR pt1  ang1 (/ caplen 2)))
    (setq pt1b (POLAR pt1a ang  (/ caplen 2)))
    (setq pt1c (POLAR pt1b (+ ang1 (dtr 180)) (/ caplen 2)))
    (setq pt1d (POLAR pt1c (+ ang1 (dtr 180)) (/ caplen 2)))
    (setq pt1e (POLAR pt1a (+ ang1 (dtr 180)) caplen))
    (cond
        ((= future 1)
            (setq c_itemno (strcat c_itemno "5"))
            (if (/= dwgtype "D")(bmlist pt1c))
            (command "layer" "s" "3c" "")
        )
        ((= future 0)
            (command "layer" "s" "2h" "")
        )
    )
    (if (<= ghk endtype)
        (command "pline" pt1a "w" (if (= future 0) "0" p-wedth1) (if (= future 0) "0" p-wedth1) pt1b pt1d pt1e "")
        (progn
            (command "line" pt1a pt1e "")
            (command "arc" pt1a pt1c pt1e)
        )
    )
    (command "layer" "s" "1c" "")
    (command "line" pt1 pt2 "")
    (setq endpoint pt2)
)

(defun i-plg(/ sd pt1 pt0 pt2 ang ang1 pt1a pt1b pt1c pt1d pt1e)
    (setiso1)
    (setq c_item "PLG")
    (setq c_itemno "020")
    (sc1)
    (disc-cha sd "SCR'D")
    (set-selec i-plg1)
    (setiso2)
    (prin1)
)

(defun i-plg1()
    (setvar "osmode" 1)
    (ftt-base "PLUG")
    (setq pt2 (POLAR pt1 ang (* 2 sk1)))
    (setq pt1a (POLAR pt1  ang1 (* 1.5 sk1)))
    (setq pt1b (POLAR pt1a ang (* 1.5 sk1)))
    (setq pt1c (POLAR pt1b (+ ang1 (dtr 180)) (* 1.5 sk1)))
    (setq pt1d (POLAR pt1c (+ ang1 (dtr 180)) (* 1.5 sk1)))
    (setq pt1e (POLAR pt1a (+ ang1 (dtr 180)) (* 3 sk1)))
    (cond
        ((= future 1)
            (setq c_itemno (strcat c_itemno "5"))
            (if (/= dwgtype "D")(bmlist pt1c))
            (command "layer" "s" "3c" "")
        )
        ((= future 0)
            (command "layer" "s" "2h" "")
        )
    )
    (command "pline" pt1 "w" (if (= future 0) "0" p-wedth1) (if (= future 0) "0" p-wedth1) pt1b pt1d "c")
    (command "layer" "s" "1c" "")
    (command "line" pt1 pt2 "")
    (setq endpoint pt2)
)

(defun i-nip(/ sd pt1 pt2 ang nipple niplen niptxt1 niptxt2 niptxt3 niptxt4)
    (setiso1)
    (setq c_itemno "000")
    (sc1)
    (if (= ventdr 1)
        (if (/= sd "SCR'D")
            (progn
                (setq niptxt1 "NPT")
                (setq niptxt2 "1")
                (setq niptxt3 "PE x TE")
                (setq niptxt4 "75mm")
;                (setq c_item (strcat niptxt1 niptxt2))
                (setq c_item niptxt1)
                (disc-cha sd niptxt3)
            )
            (progn
                (setq niptxt1 "NTE")
                (setq niptxt2 "1")
                (setq niptxt3 "TBE")
                (setq niptxt4 "75mm")
;                (setq c_item (strcat niptxt1 niptxt2))
                (setq c_item niptxt1)
                (disc-cha sd niptxt3)
            )
        )
        (i-nip2)
    )
    (if (< ghk endtype)
        (set-selec i-nip1)
    )
    (setiso2)
    (if (/= ventdr 1)(if (or (= sd "PE") (= sd "TE"))(val-acc3)(if (= sd "BE")(val-acc2)(val-acc))))
    (prin1)
)

(defun i-nip1()
    (if (= job_direc 1)
        (progn
            (SETQ pt1 (GETPOINT "\nPICK 1ST POINT OF NIPPLE : "))
            (setvar "osmode" 0)
            (IF (= pt1 nil)(setq pt1 endpoint))
            (setq ang (GETANGLE pt1 "\nPICK NIPPLE DIRECTION: "))
        )
    )
    (setvar "osmode" 0)
    (IF (= pt1 nil)(setq pt1 endpoint))
    (IF (= ang nil)(setq ang endang))
    (setq pt2 (POLAR pt1 ang (* 4 sk1)))
    (cond
        ((= future 1)
            (command "layer" "s" "5c" "")
            (command "pline" pt1 "w" (if (= future 0) "0" p-wedth3) (if (= future 0) "0" p-wedth3) pt2 "")
            (setq c_itemno (strcat c_itemno "1"))
            (if (/= dwgtype "D")
                (if (= size-type 1)
                    (bmlist1 (POLAR pt1 ang (/ (distance pt1 pt2) 2)) (strcat (ch-size ghk) (chr 34) "x" niptxt4))
                    (bmlist1 (POLAR pt1 ang (/ (distance pt1 pt2) 2)) (strcat (rtos ghk 2 0) "Ax" niptxt4))
                )
            )
        )
        ((= future 0)
            (command "layer" "s" "2h" "")
            (command "line" pt1 pt2 "")
        )
    )
    (setq endpoint pt2)
    (setq endang (angle pt1 pt2))
)

(defun i-nip2()
    (setq dcl_id (load_dialog "c:/ghk/iso/valist.dcl"))
    (if (not old_point)(setq old_point '(640 480)))
    (if (not (new_dialog "nipple" dcl_id "" old_point))
        (exit)
    )
    (setq nipple 2 niplen 2)
    (set_tile "znpt" "1")
    (set_tile "z100" "1")
    (action_tile "accept" "(progn (setq x $x y $y) (setq old_point (done_dialog 1)))")
    (action_tile "znpe" "(setq nipple 1)")
    (action_tile "znpt" "(setq nipple 2)")
    (action_tile "znte" "(setq nipple 3)")
    (action_tile "z75"  "(setq niplen 1)")
    (action_tile "z100" "(setq niplen 2)")
    (action_tile "z150" "(setq niplen 3)")
    (action_tile "zsd"  "(setq sd $value)")
    (set_tile "zsd" sd)
    (setq ok(start_dialog))
    (done_dialog)
    (unload_dialog dcl_id)
    (if (= ok 1)
        (progn
            (cond
                ((= nipple 1)
                    (setq niptxt1 "NPE")
                    (setq niptxt3 "PBE")
                )
                ((= nipple 2)
                    (setq niptxt1 "NPT")
                    (setq niptxt3 "PE x TE")
                )
                ((= nipple 3)
                    (setq niptxt1 "NTE")
                    (setq niptxt3 "TBE")
                )
            )
            (cond
                ((= niplen 1)
                    (setq niptxt2 "1")
                    (setq niptxt4 "75mm")
                )
                ((= niplen 2)
                    (setq niptxt2 "2")
                    (setq niptxt4 "100mm")
                )
                ((= niplen 3)
                    (setq niptxt2 "3")
                    (setq niptxt4 "150mm")
                )
            )
:            (setq c_item (strcat niptxt1 niptxt2))
            (setq c_item niptxt1)
            (disc-cha sd niptxt3)
        )
    )
)

(defun i-gas(/ sd pt1)
    (setiso1)
    (setvar "osmode" 0)
    (setq c_item "GAS")
    (setq c_itemno "070")
    (sc1)
    (if (or (= c_disc "") (= dwgtype "D"))
        (prompt "\nIS NOT SPEC SIZE ")
        (progn
            (if (= job_direc 1)
                (SETQ pt1 (GETPOINT "\nPICK 1ST POINT OF GASKET: "))
            )
            (IF (= endang nil) (setq endang (rtd 90)))
            (ratchan)
            (IF (= pt1 nil)
                (progn
                    (setq pt1 endpoint)
                    (bmlist (POLAR pt1 endang1 (* 3 sk1)))
                )
                (bmlist pt1)
            )
        )
    )
    (setiso2)
    (prin1)
)

(defun i-blt(/ sd pt1 unitw1)
    (setiso1)
    (setvar "osmode" 0)
    (setq c_item "BLT")
    (setq c_itemno "080")
    (sc1)
    (if (or (= c_disc "") (= dwgtype "D"))
        (prompt "\nIS NOT SPEC SIZE ")
        (progn
            (if (= job_direc 1)
                (progn
                    (SETQ pt1 (GETPOINT "\nPICK 1ST POINT OF BOLT/NUT: "))
                    (terpri)
                    (setq unitw1(getstring "Do you want Bolt Q'TY <If Edit to Dialogue  [ D  or  Default ] = > :"))
                    (terpri)
                    (setq unitw1(strcase unitw1))
                )
            )
            (if (= old_sd "WAFER")
                (setq unitw1 "D")
            )
            (if (/= rat1 nil)
                (progn
                    (setq rat2 rat)
                    (setq rat rat1)
                )
            )
            (setq vallast nil)
            (if (= unitw1 "D")
                (ssbolt1)
                (ssbolt2)
            )
            (if (= unitw1 "D")(ssbolt3))
            (if (/= rat1 nil)
                (progn
                    (setq rat1 rat)
                    (setq rat rat2)
                )
            )
            (setq c_itemno "080")
            (IF (= endang nil) (setq endang (rtd 30)))
            (IF (= pt1 nil)
                (progn
                    (setq pt1 endpoint)
                    (bmlist4 (POLAR pt1 (- endang1 (dtr 180)) (* 3 sk1)) (strcat b-size "x" b-len) b-qty)
                )
                (bmlist4 pt1 (strcat b-size "x" b-len) b-qty)
            )
        )
    )
    (setiso2)
    (prin1)
)

(defun i-grat(/ pt1 pt2 ang)
    (setiso1)
    (setvar "osmode" 512)
    (SETQ pt1 (GETPOINT "\nPICK 1ST POINT OF PIPE: "))
    (setvar "osmode" 0)
    (initget 1)
    (setq ang (GETANGLE pt1 "\nPICK 2nd PIPE DIRECTION: "))
    (setq pt2 (POLAR pt1 (+ ang (dtr 180)) (* 2.2 sk1)))
    (command "break" pt1 pt2)
    (command "insert" "*c:/ghk/iso/grating" pt1 s "")
    (setiso2)
    (prin1)
)

;;;;;;;;;;;;;;
(defun pi-tag(/ ang1 p2 p1 ang p3 p4 p5 p6 p7)
    (setiso1)
    (setq t_style(getvar "textstyle"))
    (setvar "textstyle" "standard")
    (setq ang1 (rtd 0))
    (setvar "osmode" 0)
    (setvar "orthomode" 0)
    (prompt "\n ****---- TAG NUMBER ----****")
    (setq p2 (getpoint "\nSelect point :"))
    (setq p1 (getpoint P2 "\nTag center point :"))
    (setq ang (angle p1 p2))
    (setq p3 (polar p1 ang (* 5 s)))
    (setq p4 (polar p1 (+ ang1 1.5708) (* 1 s)))
    (setq p5 (polar p1 (+ ang1 -1.5708) (* 3 s)))
    (setq p6 (polar p5 ang1 (* 4 s)))
    (setq p7 (polar p5 (+ ang1 -3.14159) (* 4 s)))
    (command "layer" "s" "1C" "")
    (command "circle" p1 (* 5 s))
    (command "line"  p2 p3 "")
    (command "layer" "s" "2C" "")
    (command "text" "j" "c" p4 (* 2.2 s) "0" "PI")
    (command "text" "j" "c" p5 (* 2.2 s) "0" "313C")
    (setvar "textstyle" t_style)
    (setiso2)
)
(defun xv-tag(/ ang1 p2 p1 ang p3 p4 p5 p6 p7)
    (setiso1)
    (setq t_style(getvar "textstyle"))
    (setvar "textstyle" "standard")
    (setq ang1 (rtd 0))
    (setvar "osmode" 0)
    (setq p2 (getpoint "Select point :"))(print)
    (setq p1 (getpoint P2 "Tag center point :"))(print)
    (setq ang (angle p1 p2))
    (setq p3 (polar p1 ang (* 5 s)))
    (setq p4 (polar p1 (+ ang1 1.5708) (* 1 s)))
    (setq p5 (polar p1 (+ ang1 -1.5708) (* 3 s)))
    (setq p6 (polar p5 ang1 (* 4 s)))
    (setq p7 (polar p5 (+ ang1 -3.14159) (* 4 s)))
    (command "layer" "s" "1C" "")
    (command "circle" p1 (* 5 s))
    (command "line"  p2 p3 "")
    (command "layer" "s" "2C" "")
    (command "text" "j" "c" p4 (* 2.2 s) "0" "XV")
    (command "text" "j" "c" p5 (* 2.2 s) "0" "104C")
    (setvar "textstyle" t_style)
    (setiso2)
    (prin1)
)
;;;;;;;;;;;;;;
(defun filedw(/ ang1 tagd p2 p1 ang p3 p4 p5 p6 p7 p8)
    (setiso1)
    (setq t_style(getvar "textstyle"))
    (setvar "textstyle" "standard")
    (setq ang1 (rtd 0))
    (setvar "osmode" 0)
    (setvar "orthomode" 0)
    (setq tagd 5.5)
    (if (= tagn nil)(setq tagn "001"))
    (setq filedwend 1)
    (while filedwend
        (prompt "\n ****---- TAG NUMBER ----****")
        (setq p2 (getpoint "\nSelect point :"))
        (if (= p2 nil)
            (setq filedwend nil)
            (progn
                (setq p1 (getpoint P2 "\nTag center point :"))
                (setq ang (angle p1 p2))
                (setq p3 (polar p1 ang (* tagd s)))
                (setq p4 (polar p1 (dtr 90) (* 0.5 s)))
                (setq p5 (polar p4 (dtr 90) (* 2.5 s)))
                (setq p6 (polar p1 (dtr 0)   (* tagd s)))
                (setq p7 (polar p1 (dtr 180) (* tagd s)))
                (setq p8 (polar p1 (dtr 270) (* tagd s)))
                (command "layer" "s" "2c" "")
                (command "circle" p1 (* tagd s))
                (command "line"  p2 p3 "")
                (command "line"  p6 p7 "")
                (command "line"  p1 p8 "")
                (command "text" "j" "c" p5 (* 2 s) "0" "SW")
                (command "text" "j" "c" p4 (* 2 s) "0" tagn)
                (setq tagn(rtos (+ (atoi tagn) 1) 2 1))
                (cond
                    ((= (strlen tagn) 1)
                        (setq tagn(strcat "00" tagn))
                    )
                    ((= (strlen tagn) 2)
                        (setq tagn(strcat "0" tagn))
                    )
                )
            )
        )
    )
    (setvar "textstyle" t_style)
    (setiso2)
)

;;;;;;;;;;;;;;
(defun firstbm(/ ang1 tagd p2 p1 ang p3)
    (setiso1)
    (setq t_style(getvar "textstyle"))
    (setvar "textstyle" "standard")
    (setq ang1 (rtd 0))
    (setvar "osmode" 0)
    (setvar "orthomode" 0)
    (setq tagd 5)
    (setq filedwend 1)
    (while filedwend
        (prompt "\n ****---- TAG NUMBER ----****")
        (setq p1 (getpoint "\nSelect point :"))
        (if (= p1 nil)
            (setq filedwend nil)
            (progn
                (setq p2 (getpoint P1 "\nTag center point :"))
                (setq ang (angle p1 p2))
                (setq p3 (polar p1 ang (+ (* tagd s) 10)))
;                (setq p3 (polar p2 ang (* tagd s)))
;                (setq cor_dist(distance p1 p2))
;                (setq cor_qty(atoi (rtos (/ cor_dist 8) 2 0)))
;                (command "pline" p1 "w" "0" "0" (polar p1 ang 2))
;                (setq ii 1)
;                (repeat cor_qty
;                    (setq p4(polar p1 ang 6))
;                    (setq p5(polar p1 (+ ang (dtr 270)) 2))
;                    (command p5)
;                    (setq p6(polar p4 ang 4))
;                    (setq p7(polar p6 (+ ang (dtr 90)) 4))
;                    (command p7)
;                    (setq p1 p6)
;                    (setq ii (+ ii 1))
;                )
;                (command "")
;                (command "pedit" "l" "" "s" "")
                (command "insert" "*c:/ghk/iso/corout" p1 "" (rtd ang))
                (command "layer" "s" "2c" "")
                (command "circle" p3 (* tagd s))
                (command "text" "j" "mc" p3 (* 2.5 s) "0" "1")
            )
        )
    )
    (setvar "textstyle" t_style)
    (setiso2)
)

(defun i-sec(/ pt1 pt0 pt2 ang ang1 pt1a pt1b pt1c pt1d
                pt1e pt1f pt1g pt1h)
    (setiso1)
    (setvar "osmode" 1)
    (SETQ pt1 (GETPOINT "\nPICK 1ST POINT OF PIPE: "))
    (setvar "osmode" 0)
    (IF (= pt1 nil)(setq pt1 endpoint))
    (setq ang (GETANGLE pt1 "\nPICK PIPE CENTER DIRECTION: "))
    (IF (= ang nil)(setq ang endang))
    (setq pt0 (POLAR pt1 ang (* 2 sk1)))
    (initget 1)
    (setq ang1 (GETANGLE pt1 "\nPICK 2nd PIPE DIRECTION: "))
    (setq pt2 (POLAR pt0 ang (* 1 sk1)))
    (command "layer" "s" "1c" "")
    (setq pt3  (POLAR pt1  ang1 (* 1.5 sk1)))
    (setq pt4  (POLAR pt3  ang1 (* 1.5 sk1)))
    (setq pt5  (POLAR pt1  (+ ang1 (dtr 180)) (* 1.5 sk1)))
    (setq pt6  (POLAR pt5  (+ ang1 (dtr 180)) (* 1.5 sk1)))
    (setq pt7  (POLAR pt5  (+ ang (dtr 180)) (* 0.5 sk1)))
    (setq pt8  (POLAR pt3  (+ ang (dtr 180)) (* 0.5 sk1)))
    (setq pt9  (POLAR pt3  ang  (* 0.5 sk1)))
    (command "arc" pt4 pt9 pt1)
    (command "arc" pt1 pt7 pt6)
    (command "arc" pt1 pt8 pt4)
    (setiso2)
    (prin1)
)

(defun i-flow(/ pt1 pt2 ang ang1 pt2a pt2b)
    (setiso1)
    (setvar "osmode" 512)
    (SETQ pt1 (GETPOINT "\nPICK 1ST POINT OF FLOW: "))
    (setvar "osmode" 0)
    (IF (= pt1 nil)(setq pt1 endpoint))
    (setq ang (GETANGLE pt1 "\nPICK FLOW CENTER DIRECTION: "))
    (IF (= ang nil)(setq ang endang))
    (setq pt2 (POLAR pt1 ang (* 9 sk1)))
    (initget 1)
    (setq ang1 (GETANGLE pt1 "\nPICK 2nd FLOW DIRECTION: "))
    (if (and (<= ang1 (+ ang (dtr 10))) (>= ang1 (- ang (dtr 10))))
        (setq ang1 (GETANGLE pt1 "\nPICK 2nd FLOW DIRECTION: "))
    )
    (command "layer" "s" "2c" "")
    (setq pt2a (POLAR pt2  ang1 (* 2.5 sk1)))
    (setq pt2b (POLAR pt2  (+ ang1 (dtr 180)) (* 2.5 sk1)))
    (cond
        ((= future 1)
            (command "solid" pt1 pt2a pt2b "" "")
        )
        ((= future 0)
            (command "layer" "s" "2h" "")
            (command "pline" pt1 "w" "0" "0" pt2a pt2b "c")
        )
    )
    (setiso2)
    (prin1)
)

(defun i-specb(/ pt1 pt2 ang ang1 pt3 pt3a pt3b)
    (setiso1)
    (setvar "osmode" 33)
    (SETQ pt1 (GETPOINT "\nPICK 1ST POINT OF SPEC BRECK: "))
    (setvar "osmode" 0)
    (setq ang (GETANGLE pt1 "\nPICK DIRECTION: "))
    (setq pt2 (POLAR pt1 ang (* 9 sk1)))
    (initget 1)
    (setq ang1 (GETANGLE pt1 "\nPICK 2nd DIRECTION: "))
    (if (and (<= ang1 (+ ang (dtr 10))) (>= ang1 (- ang (dtr 10))))
        (setq ang1 (GETANGLE pt1 "\nPICK 2nd FLOW DIRECTION: "))
    )
    (setq pt3 (POLAR pt2 ang (* 2 sk1)))
    (setq pt3a (POLAR pt3  ang1 (* 1 sk1)))
    (setq pt3b (POLAR pt3  (+ ang1 (dtr 180)) (* 1 sk1)))
    (command "layer" "s" "1c" "")
    (command "line" (POLAR pt1 ang (* 2 sk1)) pt2 "")
    (command "line" pt3a pt2 pt3b "")
    (setiso2)
    (prin1)
)

(defun i-scope(/ pt1 pt2 ang ang1 pt3 pt4 pt4a pt4b pt5 pt6 pt7)
    (setiso1)
    (setvar "osmode" 33)
    (SETQ pt1 (GETPOINT "\nPICK 1ST POINT OF SCOPE : "))
    (setvar "osmode" 0)
    (SETQ pt2 (GETPOINT pt1 "\nPICK 2ND POINT OF SCOPE : "))
    (initget 1)
    (setq ang(angle pt1 pt2))
    (setq ang1 (GETANGLE pt2 "\nPICK DIRECTION: "))
    (if (and (<= ang1 (+ ang (dtr 10))) (>= ang1 (- ang (dtr 10))))
        (setq ang1 (GETANGLE pt2 "\nPICK DIRECTION: "))
    )
    (setq pt3 (POLAR pt2 ang1 (* 5 sk1)))
    (setq pt5 (POLAR pt1 ang (* 2 sk1)))
    (setq pt6 (POLAR pt5 ang1 (* 0.7 sk1)))
    (setq pt7 (POLAR pt6 ang (* 2 sk1)))
    (setq pt4 (POLAR pt3 ang1 (* 2.5 sk1)))
    (setq pt4a(POLAR pt3 ang  (* 0.5 sk1)))
    (setq pt4b(POLAR pt3 (+ ang (dtr 180)) (* 0.5 sk1)))
    (command "layer" "s" "1c" "")
    (command "line" pt5 pt2 pt4 "")
    (command "line" pt6 pt7 "")
    (command "solid" pt4 pt4a pt4b "" "")
    (setiso2)
    (prin1)
)

(defun i-hbeam(/ pt1 pt2 ang ang1 pt3 pt4 pt3a pt3b pt3c pt3d pt4a pt4b
                 pt4c pt4d pt5 pt6 pt7 pt8)
    (setiso1)
    (setvar "osmode" 33)
    (SETQ pt1 (GETPOINT "\nPICK 1ST POINT OF H-BEAM : "))
    (setvar "osmode" 0)
    (SETQ pt2 (GETPOINT pt1 "\nPICK 2ND POINT OF H-BEAM : "))
    (initget 1)
    (setq ang(angle pt1 pt2))
    (setq ang1 (GETANGLE pt1 "\nPICK DIRECTION: "))
    (if (and (<= ang1 (+ ang (dtr 10))) (>= ang1 (- ang (dtr 10))))
        (setq ang1 (GETANGLE pt1 "\nPICK DIRECTION: "))
    )
    (setq pt3 (POLAR pt1 ang (* 3 sk1)))
    (setq pt4 (POLAR pt1 (+ ang (dtr 180)) (* 3 sk1)))
    (setq pt3a (POLAR pt3 ang1 (* 2.5 sk1)))
    (setq pt3b (POLAR pt3 (+ ang1 (dtr 180)) (* 2.5 sk1)))
    (setq pt3c (POLAR pt3b (+ ang (dtr 180)) (* 0.5 sk1)))
    (setq pt3d (POLAR pt3a (+ ang (dtr 180)) (* 0.5 sk1)))
    (setq pt3e (POLAR pt3c ang1 (* 2.25 sk1)))
    (setq pt3f (POLAR pt3d (+ ang1 (dtr 180)) (* 2.25 sk1)))
    (setq pt4a (POLAR pt4 ang1 (* 2.5 sk1)))
    (setq pt4b (POLAR pt4 (+ ang1 (dtr 180)) (* 2.5 sk1)))
    (setq pt4c (POLAR pt4b (+ ang (dtr 180)) (* 0.5 sk1)))
    (setq pt4d (POLAR pt4a (+ ang (dtr 180)) (* 0.5 sk1)))
    (setq pt4e (POLAR pt4c ang1 (* 2.25 sk1)))
    (setq pt4f (POLAR pt4d (+ ang1 (dtr 180)) (* 2.25 sk1)))
    (setq pt5 (POLAR pt1 ang (* 4 sk1)))
    (setq pt6 (POLAR pt1 (+ ang (dtr 180)) (* 4 sk1)))
    (setq pt7 (POLAR pt1 ang1 (* 4 sk1)))
    (setq pt8 (POLAR pt1 (+ ang1 (dtr 180)) (* 4 sk1)))
    (command "layer" "s" "2c" "")
    (command "solid" pt3c pt3b pt3d pt3a "")
    (command "solid" pt4c pt4b pt4d pt4a "")
    (command "solid" pt4e pt3e pt4f pt3f "")
    (command "layer" "s" "1c" "")
    (command "line" pt5 pt6 "" "line" pt7 pt8 "")
    (setiso2)
    (prin1)
)
(defun ftt-base(fttbase1 /)
    (if (= job_direc 1)
        (progn
            (SETQ pt1 (GETPOINT (strcat "\nPICK 1ST POINT OF " fttbase1 " : ")))
            (setvar "osmode" 0)
            (IF (= pt1 nil)(setq pt1 endpoint))
            (setq ang (GETANGLE pt1 (strcat "\nPICK " fttbase1 " CENTER DIRECTION: ")))
        )
    )
    (setvar "osmode" 0)
    (IF (= pt1 nil)(setq pt1 endpoint))
    (IF (= ang nil)(setq ang endang))
    (setq pt0 (POLAR pt1 ang (* 2 sk1)))
    (initget 1)
    (if (= ventdr 1)
        (setq ang1 endang1)
        (progn
            (setq ang1 (GETANGLE pt0 (strcat "\nPICK 2nd " fttbase1 " DIRECTION: ")))
            (IF (and (<= ang1 (+ ang (dtr 10))) (>= ang1 (- ang (dtr 10))))
                (setq ang1 (GETANGLE pt0 (strcat "\nPICK 2nd " fttbase1 "DIRECTION: ")))
            )
        )
    )
)

(defun i-wol2(/ dcl_id mainum1 s-num lst1 lst2 lst2- lst20- lst30-)
    (setq dcl_id (load_dialog "c:/ghk/iso/iredtee.dcl"))
    (if (not (new_dialog "iweldolet" dcl_id))
        (exit)
    )
    (sslist1 "wol")
    (setq mainum1 "0")
    (setq s-num (- (atoi sizenum) 6))
    (setq lst2- (nth s-num lst2))
    (setq lst20- (nth 0 lst2-));brencht size mm
    (setq lst30- (nth 1 lst2-));brencht size inch
    (setq br-size1(atoi (nth 0 lst20-)))
    (setq br-size2(nth 0 lst30-))
    (action_tile "br_size"  "(wol_1 (setq mainum1 $value))")
    (start_list "br_size")
    (if (= size-type 1)
        (mapcar 'add_list lst30-)
        (mapcar 'add_list lst20-)
    )
    (end_list)
    (set_tile "br_size" "0")
    (setq ok(start_dialog))
    (done_dialog)
    (unload_dialog dcl_id)
)

(defun wol_1(data)
    (setq lst20- (nth 0 lst2-));brencht size mm
    (setq lst30- (nth 1 lst2-));brencht size inch
    (setq br-size1(atoi (nth (atoi data) lst20-)))
    (setq br-size2(nth (atoi data) lst30-))
)
