(defun i-swg1(/ pt1 pt2 ang ang1)
    (setiso1)
    (if (/= ghk 15)
        (progn
            (setq c_itemno "000")
            (ch-size ghk)
            (sc1)
            (if (not i-rtee)(load"c:/ghk/iso/i-tee"))
            (i-rtee)
            (setq c_itemno "010")
            (sc1)
            (if (= swg-type 1)
                (if (= ok 1)(set-selec i-swg1-1))
                (if (= ok 1)(set-selec i-swg3-1))
            )
            (setq swg-type nil)
        )
        (prompt "\nIS NOT SPEC SIZE ")
    )
    (setiso2)
    (if (or (= sd "SW") (= sd "SCR'D"))(val-acc3)(val-acc2))
    (prin1)
)

(defun i-swg2(/ pt1 pt2 ang ang1 br-size br-size1)
    (setiso1)
    (ch-size ghk)
    (setq c_itemno "000")
    (sc1)
    (if (not i-rtee)(load"c:/ghk/iso/i-tee"))
    (i-rtee)
    (setq br-size1 ghk)
    (setq ghk br-size)
    (setq br-size br-size1)
    (setq c_itemno "010")
    (sc1)
    (if (= swg-type 2)
        (if (= ok 1)(set-selec i-swg1-1))
        (if (= ok 1)(set-selec i-swg3-1))
    )
    (setq swg-type nil)
    (setiso2)
    (if (or (= sd "SW") (= sd "SCR'D"))(val-acc3)(val-acc2))
    (prin1)
)

(defun i-swg1-1()
    (swg-bas)
    (swg-bas1)
    (if (= swg-type 1)
        (command "pline" (POLAR pt1 ang1 redlen) "w" p-wedth1 p-wedth1
                 (POLAR pt1 (+ ang1 (dtr 180)) redlen)
                 (POLAR pt2 (+ ang1 (dtr 180)) (/ redlen 2))
                 (POLAR pt2 ang1 (/ redlen 2))  "c"
        )
        (command "pline" (POLAR pt1 ang1 (/ redlen 2)) "w" p-wedth1 p-wedth1
                 (POLAR pt1 (+ ang1 (dtr 180)) (/ redlen 2))
                 (POLAR pt2 (+ ang1 (dtr 180)) redlen)
                 (POLAR pt2 ang1 redlen)  "c"
        )
    )
    (command "layer" "s" "2c" "")
    (if (= size-type 1)
        (command "text" "c" (POLAR pt1 ang1 (* 8 sk1)) (* txt-h s) "30" (strcat (ch-size ghk) (chr 34) "x" (ch-size br-size) (chr 34)))
        (command "text" "c" (POLAR pt1 ang1 (* 8 sk1)) (* txt-h s) "30" (strcat (rtos ghk 2 0) "Ax" (rtos br-size 2 0) "A"))
    )
    (if (= swgend 7)
        (command "text" "c" (POLAR pt1 ang1 (* 5 sk1)) (* txt-h s) "30" "CON.RED.")
        (command "text" "c" (POLAR pt1 ang1 (* 5 sk1)) (* txt-h s) "30" "SWG.")
    )
    (if (= swg-type 1)
        (setq ghk br-size)
    )
    (command "layer" "s" "1c" "")
    (command "line" pt1 pt2 "")
    (setq endpoint pt2)
    (setq endang ang)
)


(defun i-swg3-1()
    (swg-bas)
    (swg-bas1)
    (if (= swg-type 3)
        (command "pline" (POLAR pt1 ang1 redlen) "w" p-wedth1 p-wedth1
                 (POLAR pt1 (+ ang1 (dtr 180)) redlen)
                 (POLAR pt2 (+ ang1 (dtr 180)) redlen) pt2 "c"
        )
        (command "pline" (POLAR pt1 ang1 (/ redlen 2)) "w" p-wedth1 p-wedth1
                 (POLAR pt1 (+ ang1 (dtr 180)) (/ redlen 2))
                 (POLAR pt2 (+ ang1 (dtr 180)) (/ redlen 2))
                 (POLAR pt2 ang1 (* redlen 1.5))  "c"
        )
    )
    (command "layer" "s" "2c" "")
    (if (= size-type 1)
        (command "text" "c" (POLAR pt1 ang1 (* 8 sk1)) (* txt-h s) "30" (strcat (ch-size ghk) (chr 34) "x" (ch-size br-size) (chr 34)))
        (command "text" "c" (POLAR pt1 ang1 (* 8 sk1)) (* txt-h s) "30" (strcat (rtos ghk 2 0) "Ax" (rtos br-size 2 0) "A"))
    )
    (if (= swgend 7)
        (command "text" "c" (POLAR pt1 ang1 (* 5 sk1)) (* txt-h s) "30" "ECC.RED.")
        (command "text" "c" (POLAR pt1 ang1 (* 5 sk1)) (* txt-h s) "30" "ECC.SWG.")
    )
    (if (= swg-type 3)
        (progn
            (command "dim" "al" (POLAR pt1 ang (* 3 sk1))
                    (POLAR (POLAR pt2 (+ ang1 (dtr 180)) (/ redlen 2)) (+ ang (dtr 180)) (* 3 sk1))
                    (POLAR pt1 ang (* 3 sk1)) (rtos (- (/ (atof ma-dia) 2) (/ (atof br-dia) 2)) 2 0) "E"
            )
            (setq ghk br-size)
        )
        (command "dim" "al" (POLAR pt1 ang (* 3 sk1))
                (POLAR (POLAR pt2 ang1 (/ redlen 2)) (+ ang (dtr 180)) (* 3 sk1))
                (POLAR pt1 ang (* 3 sk1)) (rtos (- (/ (atof br-dia) 2) (/ (atof ma-dia) 2)) 2 0) "E"
        )
    )
    (if (= swg-type 3)
        (setq pt2 (POLAR pt2 (+ ang1 (dtr 180)) (/ redlen 2)))
        (setq pt2 (POLAR pt2 ang1 (/ redlen 2)))
    )
    (command "layer" "s" "1c" "")
    (command "line" pt1 (POLAR pt1 ang (* 4 sk1)) "")
    (command "line" pt2 (POLAR pt2 (+ ang (dtr 180)) (* 4 sk1)) "")
    (setq endpoint pt2)
    (setq endang ang)
)

(defun swg-bas()
    (if (= job_direc 1)
        (progn
            (setvar "osmode" 1)
            (SETQ pt1 (GETPOINT "\nPICK 1ST POINT OF SWG. RED : "))
            (setvar "osmode" 0)
            (IF (= pt1 nil)(setq pt1 endpoint))
            (setq ang (GETANGLE pt1 "\nPICK 2nd SWG. RED DIRECTION: "))
        )
    )
    (setvar "osmode" 0)
    (IF (= pt1 nil)(setq pt1 endpoint))
    (IF (= ang nil)(setq ang endang))
    (setq pt2 (POLAR pt1 ang (* 6 sk1)))
    (initget 1)
    (setq ang1 (GETANGLE pt2 "\nPICK SWG. RED DIRECTION: "))
    (if (and (<= ang1 (+ ang (dtr 10))) (>= ang1 (- ang (dtr 10))))
        (setq ang1 (GETANGLE pt2 "\nPICK SWG. RED DIRECTION: "))
    )
)

(defun swg-bas1()
    (cond
        ((= future 1)
            (if (/= swgend 7)
                (disc-cha sd swgend1)
            )
            (cond
                ((= swgend 1)
                    (if (or (= swg-type 1) (= swg-type 2))
                        (setq c_item "CSBP")
                        (setq c_item "ESBP")
                    )
                )
                ((= swgend 2)
                    (if (or (= swg-type 1) (= swg-type 2))
                        (setq c_item "CSBT")
                        (setq c_item "ESBT")
                    )
                )
                ((= swgend 3)
                    (if (or (= swg-type 1) (= swg-type 2))
                        (setq c_item "CSPE")
                        (setq c_item "ESPE")
                    )
                )
                ((= swgend 4)
                    (if (or (= swg-type 1) (= swg-type 2))
                        (setq c_item "CSTE")
                        (setq c_item "ESTE")
                    )
                )
                ((= swgend 5)
                    (if (or (= swg-type 1) (= swg-type 2))
                        (setq c_item "CSPT")
                        (setq c_item "ESPT")
                    )
                )
                ((= swgend 6)
                    (if (or (= swg-type 1) (= swg-type 2))
                        (setq c_item "CSTP")
                        (setq c_item "ESTP")
                    )
                )
                ((= swgend 7)
                    (if (or (= swg-type 1) (= swg-type 2))
                        (setq c_item "CRE")
                        (setq c_item "ERE")
                    )
                )
            )
            (setq c_itemno (strcat c_itemno "4"))
            (if (/= dwgtype "D")
                (if (= size-type 1)
                    (bmlist1 (POLAR pt1 ang1 (* 3 sk1)) (strcat (ch-size ghk) (chr 34) "x" (ch-size br-size) (chr 34)))
                    (bmlist1 (POLAR pt1 ang1 (* 3 sk1)) (strcat (rtos ghk 2 0) "Ax" (rtos br-size 2 0) "A"))
                )
            )
            (command "layer" "s" "3c" "")
            (if (= swgend 7)
                (progn
                    (setq redlen (* 3 sk1))
                    (command "insert" "c:/ghk/iso/isoweld" pt1 sk1 "" "")
                    (if (= swg-type 3)
                        (command "insert" "c:/ghk/iso/isoweld" (POLAR pt2 (+ ang1 (dtr 180)) (/ redlen 2)) sk1 "" "")
                        (if (= swg-type 4)
                            (command "insert" "c:/ghk/iso/isoweld" (POLAR pt2 ang1 (/ redlen 2)) sk1 "" "")
                            (command "insert" "c:/ghk/iso/isoweld" pt2 sk1 "" "")
                        )
                    )
                )
                (setq redlen (* 1.5 sk1))
            )
        )
        ((= future 0)
            (command "layer" "s" "2h" "")
            (if (= swgend 7)
                (progn
                    (setq redlen (* 3 sk1))
                    (command "circle" pt1 sk1)
                    (if (= swg-type 3)
                        (command "circle" (POLAR pt2 (+ ang1 (dtr 180)) (/ redlen 2)) sk1)
                        (if (= swg-type 4)
                            (command "circle" (POLAR pt2 ang1 (/ redlen 2)) sk1)
                            (command "circle" pt2 sk1)
                        )
                    )
                )
                (setq redlen (* 1.5 sk1))
            )
        )
    )
)
