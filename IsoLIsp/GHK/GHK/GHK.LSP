(defun s::startup ()
    (vmon)
    (setq sca 1)
    (command "cmdecho" "0")
    (load"c:/ghk/layer1")
    (load"c:/ghk/hotkey")
)
(defun tan (a)
  (/ (sin a) (cos a))
)
(defun dtr (a)
	(* pi (/ a 180.0))
)

(defun rtd (a)
	(/ (* a 180.0) pi)
)
(defun fix1 (a)
    (atoi (rtos a 2 0))
)
(defun se1()
  (setq olderr *error* *error* ghkerr)
  (command "cmdecho" "0")
  (command "UNDO" "GROUP")
  (setvar "cmdecho" 0)
  (SETQ A (SSGET))
  (layer1)
  (graphscr)
)
(defun se2()
    (setq olderr *error* *error* ghkerr)
    (command "cmdecho" "0")
    (dim-scale)
    (layer1)
    (graphscr)
    (setq la (getvar "clayer"))
    (setq orth(getvar "orthomode"))
    (setq os(getvar "osmode"))
    (command "orthomode" "1")
    (command "UNDO" "GROUP")
    (setvar "cmdecho" 0)
    (if (= ghk nil)
       (progn
        (setq ghk 50)
            (IF (not pdd50)
                (load"c:/ghk/lsp/design")
            )
        (pdd50)
       )
    )
    (RESETGHK)
    (initget 1)
)
(defun se3()
    (setq olderr *error* *error* ghkerr)
    (setvar "cmdecho" 0)
    (dim-scale)
    (layer1)
    (graphscr)
    (setq la (getvar "clayer"))
    (setq orth(getvar "orthomode"))
    (setq os(getvar "osmode"))
    (command "orthomode" "1")
    (command "dimtix" "1")
    (command "UNDO" "GROUP")
    (command "cmdecho" "0")
    (initget 1)
)
(defun se4()
    (setq olderr *error* *error* ghkerr)
    (dim-scale)
    (layer1)
    (graphscr)
    (setq la (getvar "clayer"))
    (setq orth(getvar "orthomode"))
    (setq os(getvar "osmode"))
    (command "orthomode" "1")
    (setvar "cmdecho" 0)
    (command "UNDO" "GROUP")
    (command "dimtix" "1")
    (command "cmdecho" "0")
    (initget 1)
)
(defun se5()
    (setq olderr *error* *error* ghkerr)
    (dim-scale)
    (layer1)
    (graphscr)
    (setq la (getvar "clayer"))
    (setq orth(getvar "orthomode"))
    (setq os(getvar "osmode"))
    (command "orthomode" "1")
    (command "UNDO" "GROUP")
    (setvar "cmdecho" 0)
)
(defun se6()
    (setq olderr *error* *error* ghkerr)
    (setvar "orthomode" orth)
    (setvar "osmode" 37)
    (command "layer" "s" la "")
    (command "UNDO" "END")
)
(defun c:set1 ()
 (graphscr)
 (setvar "cmdecho" 0)
 (if (/= num1 nil)
     (if (> (atof num1) 6)
         (setq num1 "1")
     )
 )
)

(defun c:set2 ()
 (setvar "clayer" la)
 (setvar "osmode" os)
 (command "UNDO" "END")
)
(defun c:lst1 ()
 (command "point" '(0 0))
 (entdel (setq lst(entlast)))
 (setq add(ssadd))
)

(defun c:lst2 ()
 (setq lst(entlast))
 (setq add(ssadd))
 (setq add(ssadd lst add))
)

(defun ss-add ()
 (while (setq lst(entnext lst))
        (ssadd lst add)
 )
)

(defun layerch(a1 / a)
    (se1)
    (IF (/= a nil)
        (COMMAND "CHPROP" A "" "la" a1 "C" "BYLAYER" "LT" "BYLAYER" "" )
    )
)
(defun dim-scale()
    (setq dwgscale(getvar "dimscale"))
    (if (/= dwgscale s)(load"GHK"))
)
(defun ghkerr (jjj)
    (if (/= jjj "\nFunction cancelled")
        (princ (strcat "\nError : " jjj))
    )
    (command "layer" "s" la "")
    (setvar "osmode" os)
    (setvar "orthomode" orth)
)
(defun dwg-scale()
       (command "ltscale" s)
       (command "limits" "" (list (* s maxy)(* s maxx)))
       (command "dim" "dimscale" s "e")
       (command "zoom" "a")
       (setq menu-sel(strcase (getvar "menuname")))
       (cond
            ((= menu-sel "GHKBASE")
            (command "vslide" "ghkbase")
        )
        ((or (= menu-sel "C:\\GHK\\KIC") (= menu-sel "KIC"))
            (load"c:/ghk/lsp/planbase")
            (princ "\nPiping Plan Loading...................")
        )
        ((or (= menu-sel "C:\\GHK\\D-ISO") (= menu-sel "D-ISO"))
            (load"c:/ghk/iso/detail")
            (princ "\nPiping ISO Loading...................")
        )
        ((or (= menu-sel "C:\\GHK\\STRU") (= menu-sel "STRU"))
            (load"c:/ghk/stru/col-base")
            (princ "\nSteel Cad Shop Loading...................")
        )
        ((or (= menu-sel "C:\\GHK\\ISO") (= menu-sel "ISO"))
            (load"c:/ghk/iso/iso-base")
            (isobase)
            (princ "\nPiping ISO Loading...................")
        )
    )
)
(setq s (getvar "dimscale"))
(setq menu-sel(strcase (getvar "menuname")))
(cond
    ((or (= menu-sel "C:\\GHK\\KIC") (= menu-sel "KIC"))
        (load "c:/ghk/lsp/planbase")
        (load "c:/ghk/dim")
        (princ "\nPiping Plan Loading...................")
    )
    ((or (= menu-sel "C:\\GHK\\D-ISO") (= menu-sel "D-ISO"))
        (load "c:/ghk/iso/detail")
        (load "c:/ghk/dim")
        (princ "\nPiping ISO Loading...................")
    )
    ((or (= menu-sel "C:\\GHK\\STRU") (= menu-sel "STRU"))
        (load "c:/ghk/stru/col-base")
        (load "c:/ghk/dim1")
        (princ "\nSteel Cad Shop Loading...................")
    )
    ((or (= menu-sel "C:\\GHK\\ISO") (= menu-sel "ISO"))
        (load "c:/ghk/iso/iso-base")
        (load "c:/ghk/dim")
        (isobase)
        (princ "\nPiping ISO Loading...................")
    )
)
