;;;;;;tag lisp
(defun tag1(/ d t p1 p2 ang p3)
    (se4)
    (setq d (* s 5))
    (setq t (* s 2.2))
    (command "orthomode" 0)
    (command "osmode" 0)
    (setq p2 (getpoint "Select point :"))(print)
    (setq p1 (getpoint p2 "Tag center point :"))(print)
    (setq ang (angle p1 p2))
    (setq p3 (polar p1 ang d))
    (command "layer" "s" "2c" "")
    (command "circle" p1 d )
    (command "dim" "lea" p2 p3 ^c "e")
    (command "text" "j" "m" p1 t "0" "1")
    (se6)
)
;;;;;;;;;;;;;;
(defun tag2(/ la orth os d t t1 t2 t3 ang1 p1 p2 ang p3 p4 p5 p6 p7)
    (se4)
    (command "orthomode" 0)
    (command "osmode" 0)
    (setq d (* s 5))
    (setq t (* s 2.2))
    (setq t1 (* s 1))
    (setq t2 (* s 3))
    (setq t3 (* s 4))
    (setq ang1 (rtd 0))
    (setq p2 (getpoint "Select point :"))(print)
    (setq p1 (getpoint P2 "Tag center point :"))(print)
    (setq ang (angle p1 p2))
    (setq p3 (polar p1 ang d))
    (setq p4 (polar p1 (+ ang1 1.5708) t1))
    (setq p5 (polar p1 (+ ang1 -1.5708) t2))
    (setq p6 (polar p5 ang1 t3))
    (setq p7 (polar p5 (+ ang1 -3.14159) t3))
    (command "layer" "s" "2C" "")
    (command "circle" p1 d )
    (command "line"  p2 p3 "")
    (command "text" "j" "c" p4 t "0" "PI")
    (command "text" "j" "C" p5 t "0" "2401")
    (se6)
)
;;;;;;;;;;;;;;;;;;;
(defun tag3(/ la orth os d t t1 t2 ang1 p2 p1 ang p3 p4 p5 p6 p7)
    (se4)
    (command "layer" "s" "2C" "")
    (command "orthomode" 0)
    (command "osmode" 0)
    (setq d (* s 5))
    (setq t (* s 2.2))
    (setq t1 (* s 1))
    (setq t2 (* s 3.5))
    (setq ang1 (rtd 0))
    (setq p2 (getpoint "Select point :"))(print)
    (setq p1 (getpoint P2 "Tag center point :"))(print)
    (setq ang (angle p1 p2))
    (setq p3 (polar p1 ang d))
    (setq p4 (polar p1 (+ ang1 1.5708) t1))
    (setq p5 (polar p1 (+ ang1 -1.5708) t2))
    (setq p6 (polar p1 ang1 D))
    (setq p7 (polar p1 (+ ang1 3.14159) D))
    (command "layer" "s" "2C" "")
    (command "circle" p1 d )
    (command "line"  p2 p3 "")
    (command "line"  p6 p7 "")
    (command "text" "j" "c" p4 t "0" "PI")
    (command "text" "j" "c" p5 t "0" "2104")
    (se6)
)
;;;;;;;;;;;;;;;;;;;
(defun tag4(/ la orth os d t p1 p2 ang p3)
    (se4)
    (command "layer" "s" "2C" "")
    (command "orthomode" 0)
    (command "osmode" 0)
    (setq d (* s 5))
    (setq t (* s 2.2))
    (setq p2 (getpoint "Select point :"))(print)
    (setq p1 (getpoint p2 "Tag center point :"))(print)
    (setq ang (angle p1 p2))
    (setq p3 (polar p1 ang d))
    (command "layer" "s" "2C" "")
    (command "circle" p1 d )
    (command "dim" "lea" p2 p3 ^c "e")
    (se6)
)
;;;;;;;;;;;;;;;;;;
(defun tag5(/ p2 p1 ang p3 p4)
    (se4)
    (command "layer" "s" "2C" "")
    (command "osmode" 4)
    (setq p2 (getpoint "Select point :" ))
    (command "osmode" 0)
    (setq p1 (getpoint P2 "Tag center point :"))
    (setq ang(angle p2 p1))
    (setq p3 (polar p2 ang (* s 10)))
    (setq p4 (polar p3 (+ ang (dtr 180)) (* s 5)))
    (command "layer" "s" "1C" "")
    (command "circle" p3 "d" (* s 10))
    (command "line"  p2 p4 "")
    (command "layer" "s" "5C" "")
    (command "text" "j" "m" p3 (* s 4) "0" "A")
    (se6)
)
;;;;;;;;;;;;;;;;;;
(defun tag6(/ la orth os d d1 t t1 t2 ang p3 p4 p5 p6 p7)
    (se4)
    (command "layer" "s" "2C" "")
    (setq d (* s 10))
    (setq t (* s 2.2))
    (setq t1 (* s 1))
    (setq t2 (* s 3.5))
    (command "osmode" 32)
    (setq p2 (getpoint "Select point :" ))
    (command "osmode" 0)
    (setq p1 (getpoint P2 "Tag center point :"))
    (setq ang(angle p2 p1))
    (setq p3 (polar p2 ang (* d 3)))
    (setq p4 (polar p3 1.5708 t1))
    (setq p5 (polar p3 -1.5708 t2))
    (setq p6 (polar p3 0 (/ D 2)))
    (setq p7 (polar p3 3.14159 (/ D 2)))
    (command "layer" "s" "2C" "")
    (command "circle" p3 "d" d )
    (command "line"  p6 p7 "")
    (command "text" "j" "c" p4 t "0" "XV")
    (command "text" "j" "c" p5 t "0" "123")
    (se6)
)
;;;;;;tag lisp
(defun tag7(/ la orth os d t p2 p1 ang a a1 a2 a3 p3 p4 p5 p6 p7 p8 p9)
    (se4)
    (command "layer" "s" "2C" "")
    (command "orthomode" 0)
    (setq d (* s 5))
    (setq t (* s 2.2))
    (command "osmode" 0)
    (setq p2 (getpoint "Select point :"))(print)
    (setq p1 (getpoint p2 "Tag center point :"))(print)
    (setq ang (angle p1 p2))
    (setq a (angle p2 p1))
    (setq a1 (+ a 1.5708))
    (setq a2 (- a 1.5708))
    (setq a3 (- a 3.14159))
    (setq p3 (polar p1 ang d))
    (setq p4 (polar p2 a1 (/ t 3)))
    (setq p5 (polar p4 a1 (/ t 3)))
    (setq p6 (polar p4 a (/ t 6)))
    (setq p7 (polar p2 a2 (/ t 3)))
    (setq p8 (polar p7 a2 (/ t 3)))
    (setq p9 (polar p7 a3 (/ t 6)))
    (command "layer" "s" "2C" "")
    (command "arc" p5 p6 p2)
    (command "arc" p2 p9 p8)
    (command "circle" p1 d )
    (command "dim" "lea" p2 p3 ^c "e")
    (command "text" "j" "m" p1 t "0" "1")
    (se6)
)
;;;;;;tag lisp
(defun tag8(/ la orth os d t th p1 p2 a b a1 a2 a3 p3 p31 p4 p41 p5 p51)
    (se4)
    (command "layer" "s" "2C" "")
    (command "orthomode" 0)
    (setq d (* s 5))
    (setq t (* s 3))
    (setq th (* s 0.5))
    (setq p1 (getpoint "Select point :"))(print)
    (setq p2 (getpoint p1 "Tag center point :"))(print)
    (setq a (angle p1 p2))
    (setq b (angle p2 p1))
    (setq a1 (+ a 1.5708))
    (setq a2 (- a 1.5708))
    (setq a3 (- a 3.14159))
    (setq p3 (polar p1 a d))
    (setq p31 (polar p1 a d))
    (setq p4 (polar p3 a1 th))
    (setq p41 (polar p31 a2 th))
    (setq p5 (polar p1 a (* d 3)))
    (setq p51 (polar p1 a (* d 3)))
    (command "layer" "s" "2C" "")
    (if (or (< a 1.5708)(> a 4.71239))
        (progn
            (setq ang (rtd a))
            (command "dim" "lea" p1 p5 ^c "e")
            (command "text" p4 t ang "R1"))
        (progn
             (setq ang(rtd b))
             (command "dim" "lea" p1 p51 ^c "e")
             (command "text" "j" "r" p41 t ang "R1"))
    )
    (se5)
)
