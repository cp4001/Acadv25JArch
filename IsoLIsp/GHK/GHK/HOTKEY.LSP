(defun C:C1 ()(setq ss (ssget))
              (command "change" "p" "" "p" "lt" "C1" "")
              (prin1)
)

(defun C:C2 ()(setq ss (ssget))
              (command "change" "p" "" "p" "lt" "C2" "")
              (prin1)
)

(defun C:C3 ()(setq ss (ssget))
              (command "change" "p" "" "p" "lt" "C3" "")
              (prin1)
)

(defun C:C4 ()(setq ss (ssget))
              (command "change" "p" "" "p" "lt" "C4" "")
              (prin1)
)

(defun C:C5 ()(setq ss (ssget))
              (command "change" "p" "" "p" "lt" "C5" "")
              (prin1)
)

(defun C:C6 ()(setq ss (ssget))
              (command "change" "p" "" "p" "lt" "C6" "")
              (prin1)
)

(defun C:C7 ()(setq ss (ssget))
              (command "change" "p" "" "p" "lt" "C7" "")
              (prin1)
)

(defun C:C8 ()(setq ss (ssget))
              (command "change" "p" "" "p" "lt" "C8" "")
              (prin1)
)

(defun C:C9 ()(setq ss (ssget))
              (command "change" "p" "" "p" "lt" "C9" "")
              (prin1)
)

(defun C:C10()(setq ss (ssget))
              (command "change" "p" "" "p" "lt" "C10" "")
              (prin1)
)

(defun C:C11()(setq ss (ssget))
              (command "change" "p" "" "p" "lt" "C11" "")
              (prin1)
)

(defun C:C12()(setq ss (ssget))
              (command "change" "p" "" "p" "lt" "C12" "")
              (prin1)
)

(defun C:C13()(setq ss (ssget))
              (command "change" "p" "" "p" "lt" "C13" "")
              (prin1)
)

(defun C:C14()(setq ss (ssget))
              (command "change" "p" "" "p" "lt" "C14" "")
              (prin1)
)

(defun C:C15()(setq ss (ssget))
              (command "change" "p" "" "p" "lt" "C15" "")
              (prin1)
)

(defun C:H  ()(setq ss (ssget))
              (command "change" "p" "" "p" "lt" "H " "")
              (prin1)
)

(defun C:H1 ()(setq ss (ssget))
              (command "change" "p" "" "p" "lt" "H1" "")
              (prin1)
)

(defun C:H2 ()(setq ss (ssget))
              (command "change" "p" "" "p" "lt" "H2" "")
              (prin1)
)

(defun C:H3 ()(setq ss (ssget))
              (command "change" "p" "" "p" "lt" "H3" "")
              (prin1)
)

(defun C:H4 ()(setq ss (ssget))
              (command "change" "p" "" "p" "lt" "H4" "")
              (prin1)
)

(defun C:H5 ()(setq ss (ssget))
              (command "change" "p" "" "p" "lt" "H5" "")
              (prin1)
)

(defun C:H6 ()(setq ss (ssget))
              (command "change" "p" "" "p" "lt" "H6" "")
              (prin1)
)

(defun C:H7 ()(setq ss (ssget))
              (command "change" "p" "" "p" "lt" "H7" "")
              (prin1)
)

(defun C:H8 ()(setq ss (ssget))
              (command "change" "p" "" "p" "lt" "H8" "")
              (prin1)
)

(defun C:H9 ()(setq ss (ssget))
              (command "change" "p" "" "p" "lt" "H9" "")
              (prin1)
)

(defun C:H10()(setq ss (ssget))
              (command "change" "p" "" "p" "lt" "H10" "")
              (prin1)
)
(defun C:H11()(setq ss (ssget))
              (command "change" "p" "" "p" "lt" "H11" "")
              (prin1)
)

(defun C:H12()(setq ss (ssget))
              (command "change" "p" "" "p" "lt" "H12" "")
              (prin1)
)

(defun C:H13()(setq ss (ssget))
              (command "change" "p" "" "p" "lt" "H13" "")
              (prin1)
)

(defun C:H14()(setq ss (ssget))
              (command "change" "p" "" "p" "lt" "H14" "")
              (prin1)
)

(defun C:H15()(setq ss (ssget))
              (command "change" "p" "" "p" "lt" "H15" "")
              (prin1)
)

(defun C:P1 ()(setq ss (ssget))
              (command "change" "p" "" "p" "lt" "P1" "")
              (prin1)
)

(defun C:P2 ()(setq ss (ssget))
              (command "change" "p" "" "p" "lt" "P2" "")
              (prin1)
)

(defun C:P3 ()(setq ss (ssget))
              (command "change" "p" "" "p" "lt" "P3" "")
              (prin1)
)
(defun C:P4 ()(setq ss (ssget))
              (command "change" "p" "" "p" "lt" "P4" "")
              (prin1)
)

(defun C:P5 ()(setq ss (ssget))
              (command "change" "p" "" "p" "lt" "P5" "")
              (prin1)
)

(defun C:P6 ()(setq ss (ssget))
              (command "change" "p" "" "p" "lt" "P6" "")
              (prin1)
)

(defun C:P7 ()(setq ss (ssget))
              (command "change" "p" "" "p" "lt" "P7" "")
              (prin1)
)

(defun C:P8 ()(setq ss (ssget))
              (command "change" "p" "" "p" "lt" "P8" "")
              (prin1)
)

(defun C:P9 ()(setq ss (ssget))
              (command "change" "p" "" "p" "lt" "P9" "")
              (prin1)
)

(defun C:P10()(setq ss (ssget))
              (command "change" "p" "" "p" "lt" "P10" "")
              (prin1)
)

(defun C:P11()(setq ss (ssget))
              (command "change" "p" "" "p" "lt" "P11" "")
              (prin1)
)

(defun C:P12()(setq ss (ssget))
              (command "change" "p" "" "p" "lt" "P12" "")
              (prin1)
)

(defun C:P13()(setq ss (ssget))
              (command "change" "p" "" "p" "lt" "P13" "")
              (prin1)
)

(defun C:P14()(setq ss (ssget))
              (command "change" "p" "" "p" "lt" "P14" "")
              (prin1)
)

(defun C:P15()(setq ss (ssget))
              (command "change" "p" "" "p" "lt" "P15" "")
              (prin1)
)

(defun C:BY ()(setq ss (ssget))
              (command "change" "p" "" "p" "lt" "BYLAYER" "")
              (prin1)
)

(DEFUN C:11() (PRINC "\NSELECT CHANGE COLOR OBJECT")
	       (SETQ A (SSGET))
               (COMMAND "CHPROP"  A "" "Co" "1" "")
)               

(DEFUN C:22() (PRINC "\NSELECT CHANGE COLOR OBJECT")
	       (SETQ A (SSGET))
               (COMMAND "CHPROP"  A "" "Co" "2" "")
)               

(DEFUN C:33() (PRINC "\NSELECT CHANGE COLOR OBJECT")
	       (SETQ A (SSGET))
               (COMMAND "CHPROP"  A "" "Co" "3" "")
)               

(DEFUN C:44() (PRINC "\NSELECT CHANGE COLOR OBJECT")
	       (SETQ A (SSGET))
               (COMMAND "CHPROP"  A "" "Co" "4" "")
)               

(DEFUN C:55() (PRINC "\NSELECT CHANGE COLOR OBJECT")
	       (SETQ A (SSGET))
               (COMMAND "CHPROP"  A "" "Co" "5" "")
)               

(DEFUN C:66() (PRINC "\NSELECT CHANGE COLOR OBJECT")
	       (SETQ A (SSGET))
               (COMMAND "CHPROP"  A "" "Co" "6" "")
)               

(DEFUN C:77() (PRINC "\NSELECT CHANGE COLOR OBJECT")
	       (SETQ A (SSGET))
               (COMMAND "CHPROP"  A "" "Co" "7" "")
)

(DEFUN C:88() (PRINC "\NSELECT CHANGE COLOR OBJECT")
	       (SETQ A (SSGET))
               (COMMAND "CHPROP"  A "" "Co" "8" "")
)
(DEFUN C:99() (PRINC "\NSELECT CHANGE COLOR OBJECT")
	       (SETQ A (SSGET))
               (COMMAND "CHPROP"  A "" "Co" "9" "")
)

(defun C:1 (/ A)
    (se1)
    (IF (/= a nil)
        (COMMAND "CHPROP" A "" "la" "1c" "C" "BYLAYER" "LT" "BYLAYER" "" )
    )
)

(defun C:1c (/ A)
  (se1)
  (IF (/= a nil)
  (COMMAND "CHPROP" A "" "la" "1e" "C" "BYLAYER" "LT" "BYLAYER" "" )
  )
)

(defun C:1h (/ A)
  (se1)
  (IF (/= a nil)
  (COMMAND "CHPROP" A "" "la" "1h" "C" "BYLAYER" "LT" "BYLAYER" "" )
  )
)

(defun C:1p (/ A)
  (se1)
  (IF (/= a nil)
  (COMMAND "CHPROP" A "" "la" "1p" "C" "BYLAYER" "LT" "BYLAYER" "" )
  )
)


(defun C:2 (/ A)
  (se1)
  (IF (/= a nil)
  (COMMAND "CHPROP" A "" "la" "2c" "C" "BYLAYER" "LT" "BYLAYER" "" )
  )
)

(defun C:2c (/ A)
  (se1)
  (IF (/= a nil)
  (COMMAND "CHPROP" A "" "la" "2e" "C" "BYLAYER" "LT" "BYLAYER" "" )
  )
)

(defun C:2h (/ A)
  (se1)
  (IF (/= a nil)
  (COMMAND "CHPROP" A "" "la" "2h" "C" "BYLAYER" "LT" "BYLAYER" "" )
  )
)

(defun C:2p (/ A)
  (se1)
  (IF (/= a nil)
  (COMMAND "CHPROP" A "" "la" "2p" "C" "BYLAYER" "LT" "BYLAYER" "" )
  )
)

(defun C:3 (/ A)
  (se1)
  (IF (/= a nil)
  (COMMAND "CHPROP" A "" "la" "3c" "C" "BYLAYER" "LT" "BYLAYER" "" )
  )
)

(defun C:3c (/ A)
  (se1)
  (IF (/= a nil)
  (COMMAND "CHPROP" A "" "la" "3e" "C" "BYLAYER" "LT" "BYLAYER" "" )
  )
)

(defun C:3h (/ A)
  (se1)
  (IF (/= a nil)
  (COMMAND "CHPROP" A "" "la" "3h" "C" "BYLAYER" "LT" "BYLAYER" "" )
  )
)

(defun C:3p (/ A)
  (se1)
  (IF (/= a nil)
  (COMMAND "CHPROP" A "" "la" "3p" "C" "BYLAYER" "LT" "BYLAYER" "" )
  )
)

(defun C:5 (/ A)
  (se1)
  (IF (/= a nil)
  (COMMAND "CHPROP" A "" "la" "5c" "C" "BYLAYER" "LT" "BYLAYER" "" )
  )
)

(defun C:5c (/ A)
  (se1)
  (IF (/= a nil)
  (COMMAND "CHPROP" A "" "la" "5e" "C" "BYLAYER" "LT" "BYLAYER" "" )
  )
)

(defun C:5h (/ A)
  (se1)
  (IF (/= a nil)
  (COMMAND "CHPROP" A "" "la" "5h" "C" "BYLAYER" "LT" "BYLAYER" "" )
  )
)

(defun C:5p (/ A)
  (se1)
  (IF (/= a nil)
  (COMMAND "CHPROP" A "" "la" "5p" "C" "BYLAYER" "LT" "BYLAYER" "" )
  )
)

(defun C:8 (/ A)
  (se1)
  (IF (/= a nil)
  (COMMAND "CHPROP" A "" "la" "8c" "C" "BYLAYER" "LT" "BYLAYER" "" )
  )
)

(defun C:8c (/ A)
  (se1)
  (IF (/= a nil)
  (COMMAND "CHPROP" A "" "la" "8e" "C" "BYLAYER" "LT" "BYLAYER" "" )
  )
)

(defun C:8h (/ A)
  (se1)
  (IF (/= a nil)
  (COMMAND "CHPROP" A "" "la" "8h" "C" "BYLAYER" "LT" "BYLAYER" "" )
  )
)

(defun C:8p (/ A)
  (se1)
  (IF (/= a nil)
  (COMMAND "CHPROP" A "" "la" "8p" "C" "BYLAYER" "LT" "BYLAYER" "" )
  )
)

(defun C:9 (/ A)
  (se1)
  (IF (/= a nil)
  (COMMAND "CHPROP" A "" "la" "9c" "C" "BYLAYER" "LT" "BYLAYER" "" )
  )
)

(defun C:9c (/ A)
  (se1)
  (IF (/= a nil)
  (COMMAND "CHPROP" A "" "la" "9e" "C" "BYLAYER" "LT" "BYLAYER" "" )
  )
)

(defun C:9h (/ A)
  (se1)
  (IF (/= a nil)
  (COMMAND "CHPROP" A "" "la" "9h" "C" "BYLAYER" "LT" "BYLAYER" "" )
  )
)

(defun C:9p (/ A)
  (se1)
  (IF (/= a nil)
    (COMMAND "CHPROP" A "" "la" "9p" "C" "BYLAYER" "LT" "BYLAYER" "" )
  )
)
(defun C:os ()
  (COMMAND "ddosnap")
)

(defun C:o32 ()
  (COMMAND "osmode" "32" )
)

(defun C:o37 ()
  (COMMAND "osmode" "37" )
)

(defun C:o64 ()
  (COMMAND "osmode" "64" )
)

(defun C:o4 ()
  (COMMAND "osmode" "4" )
)

(defun C:o1 ()
  (COMMAND "osmode" "1" )
)

(defun C:o0 ()
  (COMMAND "osmode" "0" )
)

(defun C:A()
       (setvar "cmdecho" 0)
       (princ " = ARRAY")
       (graphscr)
       (command "array")(prin1)
)

(defun C:ADF()
       (command "ATTDEF")(prin1)
)

(defun C:B()
       (setvar "cmdecho" 0)
       (princ " = BLOCK")
       (graphscr)
       (command "block")(prin1)
)

(defun c:bo (/ pnt1 pnt2 pnt3 pnt4)
  (se3)
  (setvar "osmode" 32)
  (setq pnt1 (getpoint "First corner of rectangle")) (terpri)
  (setq pnt3 (getcorner pnt1 "Seccond corner of rectangle")) (terpri)
  (setq pnt2 (list (car pnt1) (cadr pnt3)))
  (setq pnt4 (list (car pnt3) (cadr pnt1)))
  (command "layer" "s" "1p" "")
  (command "pline" pnt1 "w" "0" "0" pnt2 pnt3 pnt4 "c")
  (command "layer" "s" la "")
  (setvar "osmode" os)
)

(defun C:BR()
       (setvar "cmdecho" 0)
       (princ " = BREACK")
       (graphscr)
       (command "break")(prin1)
)

(defun c:bs1 (/ pnt1 pnt2 pnt3 pnt4 pnt5 pnt6 wl hl)
  (se3)
  (setvar "osmode" 32)
  (setq pnt1 (getpoint "Base point of Baseplate :")) (terpri)
  (setq wl   (getreal "Width Length [mm]:")) (terpri)
  (setq hl   (getreal "Hight Length [mm]:")) (terpri)
  (setq pnt2 (polar pnt1 (dtr 90) (/ hl 2)))
  (setq pnt3 (polar pnt2 (dtr 180) (/ wl 2)))
  (setq pnt4 (polar pnt3 (dtr 270) hl))
  (setq pnt5 (polar pnt4 (dtr 0) wl))
  (setq pnt6 (polar pnt5 (dtr 90) hl))
  (setvar "osmode" 0)
  (command "layer" "s" "5c" "")
  (command "pline" pnt3 "w" "0" "0" pnt4 pnt5 pnt6 "c")
  (command "layer" "s" "1e" "")
  (command "line" (polar pnt1 (dtr 90) (/ hl 1.8)) (polar pnt1 (dtr 270) (/ hl 1.8)) "")
  (command "line" (polar pnt1 (dtr 180) (/ wl 1.8)) (polar pnt1 (dtr 0) (/ wl 1.8)) "")
  (command "layer" "s" la "")
  (setvar "osmode" os)
)


(defun C:B2(/ os ww sno pt1 pt2 no x jjent)
    (setvar "cmdecho" 0)
    (setq os (getvar "osmode"))
    (setvar "osmode" 37)
    (princ " = BREAK2P")
    (graphscr)
    (setq ww (ssget))
    (setq sno (sslength ww))
    (setq pt1 (getpoint "\nEnter 1st Point : "))
    (setq pt2 (getpoint pt1 "\nEnter 2nd Point : "))
    (setvar "osmode" 0)
    (setq no 0)
    (repeat sno
        (setq x (ssname ww no))
        (setq jjent(cdr (assoc 0 (entget x))))
        (if (or (= "LINE" jjent) (= "LWPOLYLINE" jjent))
            (command "break" x pt1 pt2)
        )
        (setq no (1+ no))
    )
    (setvar "osmode" os)
    (prin1)
)


(defun C:CL()
       (IF (not cl)(LOAD"c:/ghk/cl"))
       (setvar "cmdecho" 0)
       (cl)
       (princ " = cloud mark")
)

(defun C:CF()
       (setvar "cmdecho" 0)
       (princ " = CHAMFER")
       (graphscr)
       (command "CHAMFER")(prin1)
)

(defun c:co (/ la orth os p1 p2 r1 p3 p4 p5 p6 p7 p8 p9)
    (setq la (getvar "clayer"))
    (setq orth(getvar "orthomode"))
    (setq os(getvar "osmode"))
    (setvar "osmode" 0)
    (setq p1 (getpoint"\nFirst Point")
          p2 (getpoint p1 "\nSecond Point")
          r1 (angle p1 p2)
          p3 (polar p1 r1 (* (distance p1 p2) 0.5))
          p4 (polar p3 (+ r1 (dtr 180)) (* s 0.5))
          p5 (polar p4 (+ r1 (dtr 180)) (* s 0.5))
          p6 (polar p4 (+ r1 (dtr 90))  (* s 4))
          p7 (polar p3 r1               (* s 0.5))
          p8 (polar p7 r1               (* s 0.5))
          p9 (polar p7 (+ r1 (dtr 270)) (* s 4))
     )
    (command "layer" "s" "1C" "")
    (command "pline" p1 p5 p6 p9 p8 p2 "")
    (setvar "orthomode" orth)
    (setvar "osmode" os)
    (command "layer" "s" la "")
)

(defun c:co1 (/ la orth os p1 p2 r1 p3 p4)
    (setq la (getvar "clayer"))
    (setq orth(getvar "orthomode"))
    (setq os(getvar "osmode"))
    (setvar "osmode" 33)
    (setq p1 (getpoint"\nFirst Point")
          p2 (getpoint p1 "\nSecond Point")
          r1 (angle p1 p2)
          p3 (polar p1 r1 (/ (distance p1 p2) 2))
          p4 (polar p3 (+ r1 (dtr 90))  (/ (distance p1 p2) 6))
    )
    (setvar "osmode" 0)
    (command "layer" "s" "1C" "")
    (command "pline" p1 p4 p2 "")
    (setvar "orthomode" orth)
    (setvar "osmode" os)
    (command "layer" "s" la "")
)

(defun c:co2 (/ la orth os p1 p2)
    (setq la (getvar "clayer"))
    (setq orth(getvar "orthomode"))
    (setq os(getvar "osmode"))
    (setvar "osmode" 33)
    (setq p1 (getpoint"\nFirst Point")
          p2 (getpoint p1 "\nSecond Point")
    )
    (co2_sub p1 p2)
    (setvar "orthomode" orth)
    (setvar "osmode" os)
    (command "layer" "s" la "")
)
(defun co2_sub (p1 p2 / r1 p3 p4 p5 p6 p7 p8 p9)
    (setq r1 (angle p1 p2)
          p3 (polar p1 r1 (/ (distance p1 p2) 2))
          p4 (polar p3 r1 (* s 0.5))
          p5 (polar p4 r1 (* s 0.5))
          p6 (polar p4 (+ r1 (dtr 90))  (* s 0.5))
          p7 (polar p3 (+ r1 (dtr 180))  (* s 0.5))
          p8 (polar p7 (+ r1 (dtr 180))  (* s 0.5))
          p9 (polar p7 (+ r1 (dtr 270))  (* s 0.5))
    )
    (setvar "osmode" 0)
    (command "layer" "s" "1C" "")
    (command "line" (polar p1 (+ r1 (dtr 180)) (* s 2)) p8 "" "line" p5 (polar p2 r1 (* s 2)) "")
    (command "arc" p9 p8 p3 "arc" p3 p5 p6)
)

(defun C:CH()
       (setvar "cmdecho" 0)
       (princ " = CHANGE")
       (command "change" "auto")(prin1)
)

(defun C:CH1()
       (setvar "cmdecho" 0)
       (princ " = CHANGE")
       (command "CHPROP")(prin1)
)

(defun c:ct (/ last_o tot_o ent o_str n_str st s_temp
               n_slen o_slen si chf chm cont ans)
  (setq objs (ssget))
  (setq chm 0)
  (if objs 
    (progn
      (if (= (type objs) 'ENAME) 
        (progn
          (setq ent (entget objs))
          (princ (strcat "\nExisting string: " (cdr (assoc 1 ent))))
        )
        (if (= (sslength objs) 1)
          (progn
            (setq ent (entget (ssname objs 0)))
            (princ (strcat "\nExisting string: " (cdr (assoc 1 ent))))
          )
        )
      )
      (setq o_str (getstring "\nMatch string   : " t))
      (setq o_slen (strlen o_str))
      (if (/= o_slen 0)
        (progn
          (setq n_str (getstring "\nNew string     : " t))
          (setq n_slen (strlen n_str))
          (setq last_o 0 
                tot_o  (if (= (type objs) 'ENAME)
                         1
                         (sslength objs)
                       )
          )
          (while (< last_o tot_o)     
            (if (or (= "TEXT"  (cdr (assoc 0 (setq ent (entget (ssname objs last_o))))))
                    (= "MTEXT" (cdr (assoc 0 (setq ent (entget (ssname objs last_o))))))
                )
              (progn
                (setq chf nil si 1)
                (setq s_temp (cdr (assoc 1 ent)))
                (while (= o_slen (strlen (setq st (substr s_temp si o_slen))))
                  (if (= st o_str)
                    (progn
                      (setq s_temp (strcat 
                                     (if (> si 1)
                                       (substr s_temp 1 (1- si)) 
                                       ""
                                     )
                                     n_str
                                     (substr s_temp (+ si o_slen))
                                   )
                      )
                      (setq chf t)    ; Found old string
                      (setq si (+ si n_slen))
                    )
                    (setq si (1+ si))
                  )
                )
                (if chf 
                  (progn            
                    (entmod (subst (cons 1 s_temp) (assoc 1 ent) ent))
                    (setq chm (1+ chm))
                  )
                )
              )
            )
            (setq last_o (1+ last_o))
          )
        )
      )
    )
  )
  (if (/= (type objs) 'ENAME)
    (if (/= (sslength objs) 1)      
      (princ (strcat "Changed "
                     (rtos chm 2 0)
                     " text lines."
             )
      )
    )
  )
)

(defun c:ct1 (/ last_o tot_o ent o_str n_str st s_temp
               n_slen o_slen si chf chm cont ans)
  (setq objs (ssget))
  (setq chm 0)
  (if objs 
    (progn
      (if (= (type objs) 'ENAME) 
        (progn
          (setq ent (entget objs))
          (princ (strcat "\nExisting string: " (cdr (assoc 1 ent))))
        )
        (if (= (sslength objs) 1)
          (progn
            (setq ent (entget (ssname objs 0)))
            (princ (strcat "\nExisting string: " (cdr (assoc 1 ent))))
          )
        )
      )
      (setq o_str "H.T.B")
      (setq o_slen (strlen o_str))
      (if (/= o_slen 0)
        (progn
          (setq n_str "T.S")
          (setq n_slen (strlen n_str))
          (setq last_o 0 
                tot_o  (if (= (type objs) 'ENAME)
                         1
                         (sslength objs)
                       )
          )
          (while (< last_o tot_o)     
            (if (or (= "TEXT"  (cdr (assoc 0 (setq ent (entget (ssname objs last_o))))))
                    (= "MTEXT" (cdr (assoc 0 (setq ent (entget (ssname objs last_o))))))
                )
              (progn
                (setq chf nil si 1)
                (setq s_temp (cdr (assoc 1 ent)))
                (while (= o_slen (strlen (setq st (substr s_temp si o_slen))))
                  (if (= st o_str)
                    (progn
                      (setq s_temp (strcat 
                                     (if (> si 1)
                                       (substr s_temp 1 (1- si)) 
                                       ""
                                     )
                                     n_str
                                     (substr s_temp (+ si o_slen))
                                   )
                      )
                      (setq chf t)    ; Found old string
                      (setq si (+ si n_slen))
                    )
                    (setq si (1+ si))
                  )
                )
                (if chf 
                  (progn            
                    (entmod (subst (cons 1 s_temp) (assoc 1 ent) ent))
                    (setq chm (1+ chm))
                  )
                )
              )
            )
            (setq last_o (1+ last_o))
          )
        )
      )
    )
  )
  (if (/= (type objs) 'ENAME)
    (if (/= (sslength objs) 1)      
      (princ (strcat "Changed "
                     (rtos chm 2 0)
                     " text lines."
             )
      )
    )
  )
)

(defun C:tj()
       (IF (not tj)(LOAD"c:/ghk/tj"))
       (setvar "cmdecho" 0)
       (C:tj)
       (graphscr)
)

(defun C:cht()
       (IF (not cht)
         (progn
          (LOAD"c:/ghk/chtext")
          (C:CHT)
         )
       )
       (setvar "cmdecho" 0)
       (princ " = change text")
)

(defun C:ha()
       (princ " = HATCH")
       (setvar "cmdecho" 0)
       (graphscr)
       (command "HATCH" )(prin1)
)


(defun C:he()
       (princ " = HATCH EDIT")
       (command "hatchedit" )
)


(defun C:HH1(/ sss high1 l i en b c d b1 C1)
    (if (not high)(setq high (* s 2.5)))
    (setq sss(ssget))
    (terpri)
    (prompt " Text Hight : <DEFAULT = ")
    (princ high)
    (prompt " > : ")
    (setq high1(getreal " "))
    (terpri)
    (if (= high1 nil)(setq high1 high)(setq high high1))
    (setq l(sslength sss))
    (setq i 0)
    (repeat l
        (setq en(ssname sss i))
        (setq b (entget en))
        (setq c (assoc 40 b))
        (setq c1 (assoc 0 b))
        (if (= (cdr c1) "TEXT")
         (progn
            (setq d (cons (car c) high1))
            (setq b1 (subst d c b))
            (entmod b1)
         )
        )
        (setq i(+ 1 i))
    )
)

(defun C:HH(/ sss high1 l i en b c d b1 C1)
    (if (not high2)(setq high2 2.5))
    (setq sss(ssget))
    (terpri)
    (prompt " Text Hight : <DEFAULT = ")
    (princ high2)
    (prompt " > : ")
    (setq high1(getreal " "))
    (terpri)
    (if (= high1 nil)(setq high1 high2)(setq high2 high1))
    (setq l(sslength sss))
    (setq i 0)
    (repeat l
        (setq en(ssname sss i))
        (setq b (entget en))
        (setq c (assoc 40 b))
        (setq c1 (assoc 0 b))
        (if (= (cdr c1) "TEXT")
         (progn
            (setq d (cons (car c) (* s high1)))
            (setq b1 (subst d c b))
            (entmod b1)
         )
        )
        (setq i(+ 1 i))
    )
)

(defun C:HW(/ sss width1 l i en b c d b1 C1)
    (if(not width)(setq width 0.65))
    (setq sss(ssget))
    (terpri)
    (prompt " Text Hight : <DEFAULT = ")
    (princ width)
    (prompt " > : ")
    (setq width1(getreal " "))
    (terpri)
    (if (= width1 nil)(setq width1 width)(setq width width1))
    (setq l(sslength sss))
    (setq i 0)
    (repeat l
        (setq en(ssname sss i))
        (setq b (entget en))
        (setq c (assoc 41 b))
        (setq c1 (assoc 0 b))
        (if (= (cdr c1) "TEXT")
         (progn
            (setq d (cons (car c) width1))
            (setq b1 (subst d c b))
            (entmod b1)
         )
        )
        (setq i(+ 1 i))
    )
)

(defun C:u0()
       (setvar "cmdecho" 0)
       (princ " = Units = 0 ")
       (setvar "dimdec" 0)
       (command "units" "2" "0" "1" "0" "0" "N")
)

(defun C:u1()
       (setvar "cmdecho" 0)
       (princ " = Units = 1 ")
       (setvar "dimdec" 1)
       (command "units" "2" "1" "1" "1" "0" "N")
)
(defun C:u2()
       (setvar "cmdecho" 0)
       (princ " = Units = 2 ")
       (setvar "dimdec" 2)
       (command "units" "2" "2" "1" "2" "0" "N")
)
(defun C:u3()
       (setvar "cmdecho" 0)
       (princ " = Units = 3 ")
       (setvar "dimdec" 3)
       (command "units" "3" "2" "1" "3" "0" "N")
)
;;;;;;auto dimension lisp
(defun c:b1(/ p1 p2 a a1 a2 a3 di d2 p3 p4 p31 p41)
    (se3)
    (setvar "osmode" 1)
    (setq p1 (getpoint "First point:"))
    (setvar "osmode" 1)
    (setq p2 (getpoint p1 "Second point:"))
    (setvar "osmode" 0)
    (command "dist" p1 p2 )
    (SETQ A (ANGLE p1 p2))
    (setq a1 (- a 3.14159))
    (setq a2 (- a 1.5708))
    (setq a3 (+ a 1.5708))
    (setq di (getvar "distance"))
    (setq di (/ di 3))
    (setq d2 (/ di 3))
    (setq p3 (polar p1 a di))
    (setq p4 (polar p3 a di))
    (setq p31(polar p3 a2 d2))
    (setq p41(polar p4 a3 d2))
    (command "layer" "s" "2C" "")
    (command "pline" p1 "w" "0" "0" p31 p41 p2 "")
    (command "pedit" "l" "s" "")
    (command "layer" "s" la "")
    (setvar "osmode" os)
    (prin1)
)
(defun C:DA(/ P1 P2 ang p3 p4 p5)
    (se3)
    (command "osmode" "32")
    (setq p1 (getpoint "Dimansion Base point :"))(print)
    (command "osmode" "0")
    (setq p2 (getpoint p1 "Dimansion Offset Direction :"))(print)
    (setq ang (angle p1 p2))
    (setq p3 (polar p1 ang (* s 20)))
    (setq p4 (polar p3 ang (* s 10)))
    (setq p5 (polar p4 ang (* s 10)))
    (command "layer" "s" "2C" "")
    (command "line" (polar p3 ang (* s 3)) (polar p3 (+ ang (dtr 180)) (* s 3)) "")
    (command "line" (polar p3 (+ ang (dtr 90)) (* s 3)) (polar p3 (+ ang (dtr 270)) (* s 3)) "")
    (command "line" (polar p4 ang (* s 3)) (polar p4 (+ ang (dtr 180)) (* s 3)) "")
    (command "line" (polar p4 (+ ang (dtr 90)) (* s 3)) (polar p4 (+ ang (dtr 270)) (* s 3)) "")
    (command "line" (polar p5 ang (* s 3)) (polar p5 (+ ang (dtr 180)) (* s 3)) "")
    (command "line" (polar p5 (+ ang (dtr 90)) (* s 3)) (polar p5 (+ ang (dtr 270)) (* s 3)) "")
    (se6)
    (prin1)
)

(defun c:te(/ sum i sss l en el text1 text k1 d1 b1)
    (setvar "cmdecho" 0)
    (setq sum 0)
    (setq i 0)
    (setq sss(ssget))
    (setq l(sslength sss))
    (repeat l
        (setq en(ssname sss i))
        (setq el (entget en))
        (setq e_text (assoc 0 el))
        (if (or (= (cdr e_text) "DIMENSION") (= (cdr e_text) "TEXT") (= (cdr e_text) "MTEXT"))
            (progn
                (setq text1 (assoc 1 el))
                (setq text (cdr (assoc 1 el)))
                (prompt "\nOld text: ") (princ text)(terpri)
                (prompt "New text: ")
                (setq k1(getstring 5 ))
                (if (= k1 "")
                    (setq k1 text)
                )
                (setq d1(cons (car text1) k1))
                (setq b1 (subst d1 text1 el))
                (entmod b1)
            )
        )
        (setq i(+ 1 i))
    )
)

(defun c:tg(/ i c_text sss l en el e_text text1 d1 b1)
    (setvar "cmdecho" 0)
    (setq i 0)
    (setq c_text(cdr (assoc 1 (entget (car (entsel "Current Text : "))))))
    (setq sss(ssget))
    (setq l(sslength sss))
    (repeat l
        (setq en(ssname sss i))
        (setq el (entget en))
        (setq e_text (assoc 0 el))
        (if (or (= (cdr e_text) "DIMENSION") (= (cdr e_text) "TEXT") (= (cdr e_text) "MTEXT"))
            (progn
                (setq text1 (assoc 1 el))
                (setq d1(cons (car text1) c_text))
                (setq b1 (subst d1 text1 el))
                (entmod b1)
            )
        )
        (setq i(+ 1 i))
    )
)

(defun c:ty(/ sum i sss l en el text1 text k1 d1 b1)
    (setvar "cmdecho" 0)
    (setq sum 0)
    (setq i 0)
    (setq sss(ssget))
    (setq l(sslength sss))
    (terpri)
    (prompt "New text: ")
    (setq k1(getstring 5 ))
    (repeat l
        (setq en(ssname sss i))
        (setq el (entget en))
        (setq text1 (assoc 1 el))
        (setq text (cdr (assoc 1 el)))
        (setq d1(cons (car text1) k1))
        (setq b1 (subst d1 text1 el))
        (entmod b1)
        (setq i(+ 1 i))
    )
)

(defun c:entt(/ sss en el)
    (setq sss(ssget))
    (setq en(ssname sss 0))
    (setq el (entget en))
)
(defun c:entt1(/ sss en el text1 text d1 b1)
    (setq sss(ssget))
    (setq en(ssname sss 0))
    (setq el (entget en))
    (setq text1 (assoc 70 el))
    (setq text (cdr (assoc 70 el)))
    (setq d1(cons (car text1) 1))
    (setq b1 (subst d1 text1 el))
    (entmod b1)
)


(defun C:pw(/ sss width1 l i en b c d b1 C1)
    (command "cmdecho" "0")
    (if (not width)(setq width 0))
    (setq sss(ssget))
    (terpri)
    (prompt " Pline Width : <Default = ")
    (princ width)
    (prompt " > : ")
    (setq width1(getstring " "))
    (terpri)
    (if (or (= width1 nil) (= width1 ""))(setq width1 width)(setq width width1))
    (setq l(sslength sss))
    (setq i 0)
    (repeat l
        (setq en(ssname sss i))
        (setq b (entget en))
        (setq c (assoc 50 b))
        (setq c1 (assoc 0 b))
        (if (= (cdr c1) "LWPOLYLINE")
            (command "pedit" en "w"  width1 "")
            (if (= (cdr c1) "LINE")
               (command "pedit" en "Y" "w"  width1  "")
            )
        )
        (setq i(+ 1 i))
    )
)

(defun C:CR()
       (setvar "cmdecho" 0)
       (princ " = CIRCLE")
       (graphscr)
       (command "circle")(prin1)
)

(defun C:D()
    (setvar "cmdecho" 0)
    (princ " = Dist :")
    (command "dist")(prin1)
)

(defun C:dd()
       (IF (not dim_edit)(LOAD"c:/ghk/dim_edit"))
       (dim_edit)
       (setvar "cmdecho" 0)
       (princ " = Dim-Edit")
)

(defun C:DS()
       (setvar "cmdecho" 0)
       (princ " = DDATTE")
       (graphscr)
       (command "ddatte")(prin1)
)
(defun C:DRE()
       (setvar "cmdecho" 0)
       (princ " = DIM ROTATE")
       (graphscr)
       (command "dim1" "trotate")(prin1)
)

(defun C:DR()
       (setvar "cmdecho" 0)
       (princ " = DDRMODES")
       (graphscr)
       (command "DDRMODES")(prin1)
)

(defun C:DO()
       (setvar "cmdecho" 0)
       (princ " = DONUT")
       (graphscr)
       (command "DONUT" "0" s )(prin1)
)

(defun C:DL()
       (setvar "cmdecho" 0)
       (princ " = DDLMODES")
       (graphscr)
       (command "DDLMODES")(prin1)
)

(defun C:DT()
       (setvar "cmdecho" 0)
       (princ " = DTEXT")
       (graphscr)
       (command "dtext")(prin1)
)                    

(defun C:de()
       (princ " = Dimtedit")
       (command "dimtedit")
)                    

(defun C:E()
       (setvar "cmdecho" 0)
       (princ " = ERASE") 
       (graphscr)
       (command "erase" "AUTO")(prin1)
)

(defun C:EC()
       (setvar "cmdecho" 0)
       (princ " = ERASE")
       (graphscr)
       (command "erase" "c")(prin1)
)

(defun C:EL()
       (setvar "cmdecho" 0)
       (princ " = ELLIPSE")
       (graphscr)
       (command "ELLIPSE")(prin1)
)

(defun C:em()
       (IF (not em)(LOAD"c:/ghk/tm"))
       (setvar "cmdecho" 0)
       (em)
       (graphscr)
       (princ " = multuple extand")
)
(defun C:EW()
       (setvar "cmdecho" 0)
       (princ " = ERASE")
       (graphscr)
       (command "erase" "w")(prin1)
)

(defun C:EP(/ ww sno no x)
    (setvar "cmdecho" 0)
    (princ " = EXPLODE")
    (graphscr)
    (setq ww (ssget))
    (setq sno (sslength ww))
    (setq no 0)
    (repeat sno
        (setq x (ssname ww no))
        (setq el (entget x))
        (if (or (= "DIMENSION" (cdr (assoc 0 el))) (= "INSERT" (cdr (assoc 0 el))) (= "LWPOLYLINE" (cdr (assoc 0 el))))
            (command "explode" x)
        )
        (setq no (1+ no))
    )
    (prin1)
)

(defun C:EPL()
       (setvar "cmdecho" 0)
       (princ " = EXPLODE LAST ")
       (command "explode" "L")
)

(defun C:ET()
       (setvar "cmdecho" 0)
       (princ " = EXTEND")
       (graphscr)
       (command "extend" "auto")(prin1)
)

(defun C:F()
       (setvar "cmdecho" 0)
       (princ " = FILLET")
       (graphscr)
       (command "fillet")(prin1)
)

(defun C:FC()
       (setvar "cmdecho" 0)
       (princ " = FILLET")
       (graphscr)
       (command "fillet" "C")(prin1)
)

(defun C:FR()
       (setvar "cmdecho" 0)
       (princ " = FILLET")
       (setq rad(getreal "\nEnter fillet radius :"))
       (graphscr)
       (setvar "filletrad" rad)(prin1)
       (command "fillet")(prin1)
)

(defun C:F0()
       (setvar "cmdecho" 0)
       (princ " = FILLET r=0 ")
       (command "fillet" "R" "0")(prin1)
       (graphscr)
       (command "fillet")(prin1)
)

(defun C:I()
       (setvar "cmdecho" 0)
       (princ " = INSERT")
       (graphscr)
       (command "insert")(prin1)
)

(defun C:Q()
       (setvar "cmdecho" 0)
       (princ " = QSAVE")
       (graphscr)
       (command "qsave")(prin1)
)

(defun C:tet()
       (IF (not tet)(LOAD"c:/ghk/i18"))
       (setvar "cmdecho" 0)
       (c:tet)
       (princ " = capture text change")
)

(defun C:i56()
       (IF (not i56)(LOAD"c:/ghk/i18"))
       (setvar "cmdecho" 0)
       (c:i56)
       (princ " = copy, mirroor block explode")
)

(defun C:L()
       (setvar "cmdecho" 0)
       (princ " = LINE")
       (graphscr)
       (command "line")(prin1)
)

(defun C:LA()
       (setvar "cmdecho" 0)
       (princ " = LAYER")
       (command "layer")(prin1)
)

(defun C:Lc()
    (setq la(cdr (assoc 8 (entget (car (entsel "Entity on dest 'n layer : "))))))
    (prompt "Slect object to change : ")
    (ssget)
    (command "change" "p" "" "p" "la" la "c" "bylayer" "lt" "bylayer" "")
)

(defun C:LI()
       (setvar "cmdecho" 0)
       (princ " = LIST")
       (command "list")(prin1)
)

(defun c:lo1(/ na-1)
   (if (not na1)(setq na1 ""))
   (terpri)
   (prompt"Load Name < ")
   (princ na1)
   (prompt " > : ")
   (setq na-1 (getstring ""))
   (if (/= na-1 "")
       (setq na1 na-1)
   )
   (command (load (strcat "c:/ghk/stru/" na1)))
)

(defun c:lo2(/ na-2)
   (if (not na2)(setq na2 ""))
   (terpri)
   (prompt"Load Name < ")
   (princ na2)
   (prompt " > : ")
   (setq na-2 (getstring ""))
   (if (/= na-2 "")
       (setq na2 na-2)
   )
   (command (load (strcat "c:/ghk/lsp/" na2)))
)

(defun c:lo3(/ na-3)
   (if (not na3)(setq na3 ""))
   (terpri)
   (prompt"Load Name < ")
   (princ na3)
   (prompt " > : ")
   (setq na-3 (getstring ""))
   (if (/= na-3 "")
       (setq na3 na-3)
   )
   (command (load (strcat "c:/ghk/iso/" na3)))
)

(defun c:lo4(/ na-4)
   (if (not na4)(setq na4 ""))
   (terpri)
   (prompt"Load Name < ")
   (princ na4)
   (prompt " > : ")
   (setq na-4 (getstring ""))
   (if (/= na-4 "")
       (setq na4 na-4)
   )
   (command (load (strcat "c:/PROGRAM FILES/AUTOCAD R14/VLISP/SAMPLE/" na4)))
)

(defun c:lo(/ na-)
   (if (not na)(setq na ""))
   (terpri)
   (prompt"Load Name < ")
   (princ na)
   (prompt " > : ")
   (setq na- (getstring ""))
   (if (/= na- "")
       (setq na na-)
   )
   (command (load na))
)

(defun C:LT()
       (setvar "cmdecho" 0)
       (princ " = LTSCALE")
       (command "ltscale")(prin1)
)

(defun C:Ls()
       (setvar "cmdecho" 0)
       (princ " = LINETYPE")
       (command "linetype")(prin1)
)

(defun C:Lm()
       (setvar "cmdecho" 0)
       (princ " = limits")
       (command "limits")(prin1)
)

(defun C:M()
       (setvar "cmdecho" 0)
       (princ " = MOVE")
       (graphscr)
       (command "move" "auto")(prin1)
)

(defun C:mo()
       (IF (not ddmodify)(LOAD"ddmodify"))
       (setvar "cmdecho" 0)
       (c:ddmodify)
       (princ " = MODIFY")
)
(defun C:MI()
       (setvar "cmdecho" 0)
       (princ " = MIRROR")
       (graphscr)
       (command "mirror" "auto")(prin1)
)

(defun C:MM()
       (setvar "cmdecho" 0)
       (princ " = MIRROR")
       (graphscr)
       (setq sss(ssget))
       (command "mirror" SSS "" pause pause "y")(prin1)
)

(defun C:C()
       (setvar "cmdecho" 0)
       (princ " = COPY")
       (graphscr)
       (COMMAND "COPY" "AUTO")
)

(defun C:CM()
       (setvar "cmdecho" 0)
       (princ " = MULTI COPY")
       (graphscr)
       (setq en (ssget))
       (COMMAND "COPY" en "" "M")
)

(defun C:mn()
       (setvar "cmdecho" 0)
       (princ " = menu")
       (COMMAND "menu")
)

(defun C:O()
       (setvar "cmdecho" 0)
       (princ " = OFFSET")
       (graphscr)
       (command "offset")(prin1)
)              

(defun C:OO()
       (setvar "cmdecho" 0)
       (princ " = OOPS")
       (command "oops")(prin1)
)


(defun C:P()
       (setvar "cmdecho" 0)
       (princ " = PAN")
       (command "pan")(prin1)
)

(defun C:PE()
       (setvar "cmdecho" 0)
       (princ " = PEDIT")
       (graphscr)
       (command "pedit")(prin1)
)

(defun C:pt()
       (IF (not pipetrim)(LOAD"c:/ghk/tm"))
       (pipetrim)
       (setvar "cmdecho" 0)
       (princ " = Pipe Trim ")
)
(defun C:PL()
       (setvar "cmdecho" 0)
       (princ " = PLINE")
       (graphscr)
       (command "pline")(prin1)
)

(defun C:PO()
       (setvar "cmdecho" 0)
       (princ " = POLYGON")
       (command "polygon")(prin1)
)

;:: CHANGE ANGLE
(defun c:pon ( / a b pnt1 pnt2 angl)
  (graphscr) 
  (setq a (entsel))
  (setq b (entget (car a)))
  (setq pnt1 (cdr (assoc 10 b)))
  (setq pnt2 (cdr (assoc 11 b)))
  (setq pnt2 (cdr (assoc 11 b)))
  (setq ang1 (angle pnt1 pnt2))
  (setvar "snapang" ang1)
)
(defun c:poff()
  (setvar "snapang" 0)
)

(defun C:R()
       (setvar "cmdecho" 0)
       (princ " = REDRAW")
       (command "redraw")(prin1)
)

(defun C:RT()
       (setvar "cmdecho" 0)
       (princ " = ROTATE")
       (graphscr)
       (command "rotate" "auto")(prin1)
)

(defun C:RE()
       (setvar "cmdecho" 0)
       (princ " = REGEN")
       (command "regen")(prin1)
)

(defun C:S()
       (setvar "cmdecho" 0)
       (princ " = STRETCH")
       (graphscr)
       (command "stretch" "c")(prin1)
)

(defun c:SR(/ pt1 pt2 pt3 pt4 pt5 pt6 tot)
   (setvar "cmdecho" 0)
   (setq os(getvar "osmode"))
   (setvar "osmode" 37)
   (while (setq pt1 (getpoint "\nFirst corner :"))
          (setq pt2 (getcorner pt1"\nOther corner :")
                tot (cons (cons pt1 pt2) tot)
                pt3 (list (car pt2) (cadr pt1))
                pt4 (list (car pt1) (cadr pt2))      )
                (grdraw pt1 pt3 6 1) (grdraw pt3 pt2 6 1)
                (grdraw pt2 pt4 6 1) (grdraw pt4 pt1 6 1)
   )
   (setq pt5 (getpoint "\nBase point :")
         pt6 (getpoint pt5 "\nNew point :")
         tot (reverse tot)
   )
   (setvar "osmode" 0)
   (foreach x tot  (command "stretch" "c" (car x) (cdr x) "" pt5 pt6))
   (setvar "osmode" os)
   (redraw) (princ)
)

(defun C:SC()
       (setvar "cmdecho" 0)
       (princ " = SCALE")
       (graphscr)
       (command "scale" "auto")(prin1)
)

(defun C:SC1()
       (setvar "cmdecho" 0)
       (princ " = SCALE")
       (graphscr)
       (setq sss(ssget))
       (command "scale" SSS "" pause "R" "30" "50")(prin1)
)

(defun C:SCR()
       (setvar "cmdecho" 0)
       (princ " = SCRIPT")
       (graphscr)
       (command "SCRIPT")(prin1)
)


(defun C:SO()
       (setvar "cmdecho" 0)
       (princ " = SOLID")
       (graphscr)
       (command "SOLID")(prin1)
)

(defun C:SSX()
       (IF (not SSX)
         (progn
           (LOAD"c:/ghk/SSX")
           (SSX)
         )
       )
)

(defun C:st()
       (setvar "cmdecho" 0)
       (princ " = style")
       (command "_style")(prin1)
)

(defun C:T()
       (setvar "cmdecho" 0)
       (princ " = TRIM")
       (graphscr)
       (command "trim" "auto")(prin1)
)

(defun C:tm()
       (IF (not tm)(LOAD"c:/ghk/tm"))
       (setvar "cmdecho" 0)
       (c:tm)
       (princ " = multuple trim")
)

(defun C:tr(/ sss t_angle1 l i en b c d b1 C1)
    (if (not t_angle)(setq t_angle 0))
    (setq sss(ssget))
    (terpri)
    (prompt " Text Angle : <Default = ")
    (princ t_angle)
    (prompt " > : ")
    (setq t_angle1(getreal " "))
    (terpri)
    (if (= t_angle1 nil)(setq t_angle1 t_angle)(setq t_angle t_angle1))
    (setq l(sslength sss))
    (setq i 0)
    (repeat l
        (setq en(ssname sss i))
        (setq b (entget en))
        (setq c (assoc 50 b))
        (setq c1 (assoc 0 b))
        (if (or (= (cdr c1) "TEXT")(= (cdr c1) "MTEXT"))
         (progn
            (setq d (cons (car c) (dtr t_angle1)))
            (setq b1 (subst d c b))
            (entmod b1)
         )
        )
        (setq i(+ 1 i))
    )
)

(defun C:mt()
       (IF (not mt)(LOAD"c:/ghk/tm"))
       (c:mt)
       (setvar "cmdecho" 0)
       (princ " = multuple trim")
)

(defun C:MS()
       (setvar "cmdecho" 0)
       (princ " = MSLIDE")
       (command "mslide")(prin1)
)

(defun C:V()
       (setvar "cmdecho" 0)
       (princ " = VIEW")
       (command "view")(prin1)
)
(defun C:Vp()
       (setvar "cmdecho" 0)
       (princ " = VPORTS")
       (command "VPORTS")(prin1)
)

(defun C:WB()
       (setvar "cmdecho" 0)
       (princ " = WBLOCK")
       (command "wblock")(prin1)
)

(defun C:'Z()
       (setvar "cmdecho" 0)
       (princ " = ZOOM")
       (command "'zoom")(prin1)
)

(defun C:W()
       (setvar "cmdecho" 0)
       (princ " = ZOOM W ")
       (command "zoom" "W")(prin1)
)

(defun C:zd()
       (setvar "cmdecho" 0)
       (princ " = ZOOM D ")
       (command "zoom" "D")(prin1)
)

(defun C:zp()
       (setvar "cmdecho" 0)
       (princ " = ZOOM P ")
       (command "zoom" "P")(prin1)
)

(defun C:za()
       (setvar "cmdecho" 0)
       (princ " = ZOOM ALL ")
       (command "zoom" "A")(prin1)
)

(defun C:h()
    (command "layer" "s" "1C" "")
    (command "_dimlinear")
)
(defun C:al()
    (setvar "cmdecho" 0)
    (princ " = DIM <Horizontal> ")
    (command "dim1" "al")(prin1)
)

(defun C:cen()
    (IF (not cen)
      (progn
        (LOAD"c:/ghk/cen")
        (c:cen)
      )
    )
)

(defun C:ang()
    (setvar "cmdecho" 0)
    (princ " = DIM <Angle> ")
    (command "dim1" "ang")(prin1)
)


(defun C:le(/ orth os dim_block dim_asz p1 p2)
    (setvar "cmdecho" 0)
    (setq la (getvar "clayer"))
    (command "layer" "s" "1C" "")
    (princ " = DIM <Leader> ")
    (setq orth (getvar "ORTHOMODE"))
    (setq os(getvar "osmode"))
    (setq dim_block (getvar "dimblk"))
    (setq dim_asz (getvar "dimasz"))
    (command "dimasz" 2.5)
    (command "dim" "dimblk" "." "e")
    (command "orthomode" "0")
    (command "osmode" "512")
    (setq p1 (getpoint "1st point:"))(terpri)
    (setq p2 (getpoint p1 "2nd point:"))(terpri)
    (command "dim" "LEA" p1 p2 "" ^c "e")(prin1)
    (command "orthomode" orth)
    (setvar "osmode" os)
    (command "dim" "dimblk" dim_block "e")
    (command "dimasz" dim_asz)
    (command "layer" "s" la "")
)


(defun C:led()
       (setvar "cmdecho" 0)
       (princ " = DIM <Leader> ")
       (command "dim" "lea" )(prin1)
)

(defun C:up(/ a)
    (setvar "cmdecho" 0)
    (princ " = DIM <updata> ")
    (setq a (ssget))
    (command "dim" "update" a "" "e")(prin1)
)

(defun C:GH()
    (setvar "dimclrd" 2)
    (setvar "dimclre" 2)
    (setvar "dimclrt" 3)
    (command "DIM1" "UP" "ALL" "")
    (if (not (tblsearch "layer" "CO"))
        (command "layer" "n" "CO" "c" "7" "CO" "lt" "continuous" "CO" "")
    )
    (if (not (tblsearch "layer" "CE"))
        (command "layer" "n" "Ce" "c" "1" "Ce" "lt" "center" "CE" "")
    )
    (if (not (tblsearch "layer" "HI"))
        (command "layer" "n" "hI" "c" "3" "hI" "lt" "hidden" "hI" "")
    )
    (if (not (tblsearch "layer" "LI"))
        (command "layer" "n" "LI" "c" "4" "LI" "lt" "phantom" "LI" "")
    )
    (if (not (tblsearch "layer" "DIM"))
        (command "layer" "n" "DIM" "c" "2" "DIM" "lt" "continuous" "DIM" "")
    )
    (if (not (tblsearch "layer" "TE"))
        (command "layer" "n" "TE" "c" "3" "TE" "lt" "continuous" "TE" "")
    )
    (if (not (ssget "X" (list (cons 8 "1C"))))
        ()
        (command "CHPROP" (ssget "X" (list (cons 8 "1C"))) "" "P" "LA" "CO" "")
    )
    (if (not (ssget "X" (list (cons 8 "1E"))))
        ()
        (command "CHPROP" (ssget "X" (list (cons 8 "1E"))) "" "P" "LA" "CE" "")
    )
    (if (not (ssget "X" (list (cons 8 "1H"))))
        ()
        (command "CHPROP" (ssget "X" (list (cons 8 "1H"))) "" "P" "LA" "HI" "")
    )
    (if (not (ssget "X" (list (cons 8 "1P"))))
        ()
        (command "CHPROP" (ssget "X" (list (cons 8 "1P"))) "" "P" "LA" "LI" "")
    )
    (if (not (ssget "X" (list (cons 8 "2C"))))
        ()
        (command "CHPROP" (ssget "X" (list (cons 8 "2C"))) "" "P" "LA" "CO" "")
    )
    (if (not (ssget "X" (list (cons 8 "2E"))))
        ()
        (command "CHPROP" (ssget "X" (list (cons 8 "2E"))) "" "P" "LA" "CE" "")
    )
    (if (not (ssget "X" (list (cons 8 "2H"))))
        ()
        (command "CHPROP" (ssget "X" (list (cons 8 "2H"))) "" "P" "LA" "HI" "")
    )
    (if (not (ssget "X" (list (cons 8 "2P"))))
        ()
        (command "CHPROP" (ssget "X" (list (cons 8 "2P"))) "" "P" "LA" "LI" "")
    )
    (if (not (ssget "X" (list (cons 8 "3C"))))
        ()
        (command "CHPROP" (ssget "X" (list (cons 8 "3C"))) "" "P" "LA" "CO" "")
    )
    (if (not (ssget "X" (list (cons 8 "3E"))))
        ()
        (command "CHPROP" (ssget "X" (list (cons 8 "3E"))) "" "P" "LA" "CE" "")
    )
    (if (not (ssget "X" (list (cons 8 "3H"))))
        ()
        (command "CHPROP" (ssget "X" (list (cons 8 "3H"))) "" "P" "LA" "HI" "")
    )
    (if (not (ssget "X" (list (cons 8 "3P"))))
        ()
        (command "CHPROP" (ssget "X" (list (cons 8 "3P"))) "" "P" "LA" "LI" "")
    )
    (if (not (ssget "X" (list (cons 8 "5C"))))
        ()
        (command "CHPROP" (ssget "X" (list (cons 8 "5C"))) "" "P" "LA" "CO" "")
    )
    (if (not (ssget "X" (list (cons 8 "5E"))))
        ()
        (command "CHPROP" (ssget "X" (list (cons 8 "5E"))) "" "P" "LA" "CE" "")
    )
    (if (not (ssget "X" (list (cons 8 "5H"))))
        ()
        (command "CHPROP" (ssget "X" (list (cons 8 "5H"))) "" "P" "LA" "HI" "")
    )
    (if (not (ssget "X" (list (cons 8 "5P"))))
        ()
        (command "CHPROP" (ssget "X" (list (cons 8 "5P"))) "" "P" "LA" "LI" "")
    )
    (if (not (ssget "X" (list (cons 8 "8C"))))
        ()
        (command "CHPROP" (ssget "X" (list (cons 8 "8C"))) "" "P" "LA" "CO" "")
    )
    (if (not (ssget "X" (list (cons 8 "8E"))))
        ()
        (command "CHPROP" (ssget "X" (list (cons 8 "8E"))) "" "P" "LA" "CE" "")
    )
    (if (not (ssget "X" (list (cons 8 "8H"))))
        ()
        (command "CHPROP" (ssget "X" (list (cons 8 "8H"))) "" "P" "LA" "HI" "")
    )
    (if (not (ssget "X" (list (cons 8 "8P"))))
        ()
        (command "CHPROP" (ssget "X" (list (cons 8 "8P"))) "" "P" "LA" "LI" "")
    )
    (if (not (ssget "X" (list (cons 8 "9C"))))
        ()
        (command "CHPROP" (ssget "X" (list (cons 8 "9C"))) "" "P" "LA" "CO" "")
    )
    (if (not (ssget "X" (list (cons 8 "9E"))))
        ()
        (command "CHPROP" (ssget "X" (list (cons 8 "9E"))) "" "P" "LA" "CE" "")
    )
    (if (not (ssget "X" (list (cons 8 "9H"))))
        ()
        (command "CHPROP" (ssget "X" (list (cons 8 "9H"))) "" "P" "LA" "HI" "")
    )
    (if (not (ssget "X" (list (cons 8 "9P"))))
        ()
        (command "CHPROP" (ssget "X" (list (cons 8 "9P"))) "" "P" "LA" "LI" "")
    )
    (command "CHPROP" (ssget "X" (list (cons 0 "TEXT"))) "" "P" "LA" "TE"  "")
    (command "CHPROP" (ssget "X" (list (cons 0 "DIMENSION"))) "" "P" "LA" "DIM"  "")
)
