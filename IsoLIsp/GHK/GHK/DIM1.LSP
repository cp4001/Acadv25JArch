(setvar "dimalt" 0)
(setvar "dimaso" 1)
(setvar "dimasz" 0.7)
(setvar "dimclrd" 1)
(setvar "dimclre" 1)
(setvar "dimclrt" 7)
(setvar "dimdli" 5)
(setvar "dimexe" 0)
(setvar "dimexo" 1)
(setvar "dimlim" 0)
(setvar "dimsoxd" 0)
(setvar "dimtad" 1)
(setvar "MIRRTEXT" 0)
(setvar "dimtih" 0)
(setvar "dimtix" 1)
(setvar "dimtofl" 1)
(setvar "dimtoh" 0)
(setvar "dimtvp" 0)
(setvar "dimtxt" 2.5)
(setvar "blipmode" 0)
(setvar "dimzin" 8)
(setvar "dimgap" 1)
(setvar "dimfit" 5)
(setvar "dimblk" "dot")
