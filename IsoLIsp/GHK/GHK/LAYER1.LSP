(defun layer2()
    (if (not (tblsearch "layer" "1c"))
        (command "layer" "n" "1c" "c" "1" "1c" "lt" "continuous" "1c" "")
    )
    (if (not (tblsearch "layer" "1e"))
        (command "layer" "n" "1e" "c" "1" "1e" "lt" "center" "1e" "")
    )
    (if (not (tblsearch "layer" "1p"))
        (command "layer" "n" "1p" "c" "1" "1p" "lt" "phantom" "1p" "")
    )
    (if (not (tblsearch "layer" "1h"))
        (command "layer" "n" "1h" "c" "1" "1h" "lt" "hidden" "1h" "")
    )
    (if (not (tblsearch "layer" "2c"))
        (command "layer" "n" "2c" "c" "7" "2c" "lt" "continuous" "2c" "")
    )
    (if (not (tblsearch "layer" "2e"))
        (command "layer" "n" "2e" "c" "7" "2e" "lt" "center" "2e" "")
    )
    (if (not (tblsearch "layer" "2p"))
        (command "layer" "n" "2p" "c" "7" "2p" "lt" "phantom" "2p" "")
    )
    (if (not (tblsearch "layer" "2h"))
        (command "layer" "n" "2h" "c" "7" "2h" "lt" "hidden" "2h" "")
    )
    (if (not (tblsearch "layer" "3c"))
        (command "layer" "n" "3c" "c" "2" "3c" "lt" "continuous" "3c" "")
    )
    (if (not (tblsearch "layer" "3e"))
        (command "layer" "n" "3e" "c" "2" "3e" "lt" "center" "3e" "")
    )
    (if (not (tblsearch "layer" "3p"))
        (command "layer" "n" "3p" "c" "2" "3p" "lt" "phantom" "3p" "")
    )
    (if (not (tblsearch "layer" "3h"))
        (command "layer" "n" "3h" "c" "2" "3h" "lt" "hidden" "3h" "")
    )
    (if (not (tblsearch "layer" "5c"))
        (command "layer" "n" "5c" "c" "3" "5c" "lt" "continuous" "5c" "")
    )
    (if (not (tblsearch "layer" "5e"))
        (command "layer" "n" "5e" "c" "3" "5e" "lt" "center" "5e" "")
    )
    (if (not (tblsearch "layer" "5p"))
        (command "layer" "n" "5p" "c" "3" "5p" "lt" "phantom" "5p" "")
    )
    (if (not (tblsearch "layer" "5h"))
        (command "layer" "n" "5h" "c" "3" "5h" "lt" "hidden" "5h" "")
    )
    (if (not (tblsearch "layer" "8c"))
        (command "layer" "n" "8c" "c" "4" "8c" "lt" "continuous" "8c" "")
    )
    (if (not (tblsearch "layer" "8e"))
        (command "layer" "n" "8e" "c" "4" "8e" "lt" "center" "8e" "")
    )
    (if (not (tblsearch "layer" "8p"))
        (command "layer" "n" "8p" "c" "4" "8p" "lt" "phantom" "8p" "")
    )
    (if (not (tblsearch "layer" "8h"))
        (command "layer" "n" "8h" "c" "4" "8h" "lt" "hidden" "8h" "")
    )
    (if (not (tblsearch "layer" "9c"))
        (command "layer" "n" "9c" "c" "6" "9c" "lt" "continuous" "9c" "")
    )
    (if (not (tblsearch "layer" "9e"))
        (command "layer" "n" "9e" "c" "6" "9e" "lt" "center" "9e" "")
    )
    (if (not (tblsearch "layer" "9p"))
        (command "layer" "n" "9p" "c" "6" "9p" "lt" "phantom" "9p" "")
    )
    (if (not (tblsearch "layer" "9h"))
        (command "layer" "n" "9h" "c" "6" "9h" "lt" "hidden" "9h" "")
    )
    (if (not (tblsearch "layer" "rev"))
        (command "layer" "n" "rev" "c" "1" "rev" "lt" "continuous" "rev" "")
    )
    (if (not (tblsearch "layer" "ghkiso"))
        (command "layer" "n" "ghkiso" "c" "6" "ghkiso" "lt" "continuous" "ghkiso" "")
    )
    (if (not (tblsearch "layer" "autobm"))
        (command "layer" "n" "autobm" "c" "6" "autobm" "lt" "continuous" "autobm" "")
    )
)

(defun layer1()
    (if (not (tblsearch "layer" "1c"))
        (command "layer" "n" "1c" "c" "1" "1c" "lt" "continuous" "1c" "")
    )
    (if (not (tblsearch "layer" "1e"))
        (command "layer" "n" "1e" "c" "1" "1e" "lt" "center" "1e" "")
    )
    (if (not (tblsearch "layer" "1p"))
        (command "layer" "n" "1p" "c" "1" "1p" "lt" "phantom" "1p" "")
    )
    (if (not (tblsearch "layer" "1h"))
        (command "layer" "n" "1h" "c" "1" "1h" "lt" "hidden" "1h" "")
    )
    (if (not (tblsearch "layer" "2c"))
        (command "layer" "n" "2c" "c" "7" "2c" "lt" "continuous" "2c" "")
    )
    (if (not (tblsearch "layer" "2e"))
        (command "layer" "n" "2e" "c" "7" "2e" "lt" "center" "2e" "")
    )
    (if (not (tblsearch "layer" "2p"))
        (command "layer" "n" "2p" "c" "7" "2p" "lt" "phantom" "2p" "")
    )
    (if (not (tblsearch "layer" "2h"))
        (command "layer" "n" "2h" "c" "7" "2h" "lt" "hidden" "2h" "")
    )
    (if (not (tblsearch "layer" "3c"))
        (command "layer" "n" "3c" "c" "2" "3c" "lt" "continuous" "3c" "")
    )
    (if (not (tblsearch "layer" "3e"))
        (command "layer" "n" "3e" "c" "2" "3e" "lt" "center" "3e" "")
    )
    (if (not (tblsearch "layer" "3p"))
        (command "layer" "n" "3p" "c" "2" "3p" "lt" "phantom" "3p" "")
    )
    (if (not (tblsearch "layer" "3h"))
        (command "layer" "n" "3h" "c" "2" "3h" "lt" "hidden" "3h" "")
    )
    (if (not (tblsearch "layer" "5c"))
        (command "layer" "n" "5c" "c" "3" "5c" "lt" "continuous" "5c" "")
    )
    (if (not (tblsearch "layer" "5e"))
        (command "layer" "n" "5e" "c" "3" "5e" "lt" "center" "5e" "")
    )
    (if (not (tblsearch "layer" "5p"))
        (command "layer" "n" "5p" "c" "3" "5p" "lt" "phantom" "5p" "")
    )
    (if (not (tblsearch "layer" "5h"))
        (command "layer" "n" "5h" "c" "3" "5h" "lt" "hidden" "5h" "")
    )
    (if (not (tblsearch "layer" "8c"))
        (command "layer" "n" "8c" "c" "4" "8c" "lt" "continuous" "8c" "")
    )
    (if (not (tblsearch "layer" "8e"))
        (command "layer" "n" "8e" "c" "4" "8e" "lt" "center" "8e" "")
    )
    (if (not (tblsearch "layer" "8p"))
        (command "layer" "n" "8p" "c" "4" "8p" "lt" "phantom" "8p" "")
    )
    (if (not (tblsearch "layer" "8h"))
        (command "layer" "n" "8h" "c" "4" "8h" "lt" "hidden" "8h" "")
    )
    (if (not (tblsearch "layer" "9c"))
        (command "layer" "n" "9c" "c" "6" "9c" "lt" "continuous" "9c" "")
    )
    (if (not (tblsearch "layer" "9e"))
        (command "layer" "n" "9e" "c" "6" "9e" "lt" "center" "9e" "")
    )
    (if (not (tblsearch "layer" "9p"))
        (command "layer" "n" "9p" "c" "6" "9p" "lt" "phantom" "9p" "")
    )
    (if (not (tblsearch "layer" "9h"))
        (command "layer" "n" "9h" "c" "6" "9h" "lt" "hidden" "9h" "")
    )
    (if (not (tblsearch "layer" "rev"))
        (command "layer" "n" "rev" "c" "1" "rev" "lt" "continuous" "rev" "")
    )
    (if (not (tblsearch "layer" "ghkiso"))
        (command "layer" "n" "ghkiso" "c" "6" "ghkiso" "lt" "continuous" "ghkiso" "")
    )
    (if (not (tblsearch "layer" "autobm"))
        (command "layer" "n" "autobm" "c" "6" "autobm" "lt" "continuous" "autobm" "")
    )
)
