;;;;;;;;;;;;;;;y-type strainer top lisp
(defun y-strf (/ la orth os a-pip k-pip flglen flgd flghd flgthk hubdia
                 stubl stubl1 stubd vall vall1 vall2 len p1 p2 ang ang1
                 vall-1 str1 str11 str111 str1111
                 str2 str21 str211 str2111 str3 str31 str4 str41 str5
                 str51 str511 str512 str513 str6 str61 str62 str63)
    (strset)
;<<<<<<<<<<<<<<<<<<<<<   strainer  dwg
    (if (or (= flg_end "F") (= flg_end "W"))
        (progn
            (setq str1 (polar (polar p2 (+ ang (dtr 90)) flghd) ang g))
            (setq str2 (polar str1 ang (- len (* g 2))))
        )
        (progn
            (setq str1 (polar p2 (+ ang (dtr 90)) flghd))
            (setq str2 (polar str1 ang len))
        )
    )
    (setq str11 (polar str1 ang flgthk))
    (setq str111 (polar str11 (+ ang (dtr 270)) (- flghd piphd)))
    (setq str1111 (polar str111 (+ ang (dtr 270)) pipd ))
    (setq str21 (polar str2 (+ ang (dtr 180)) flgthk))
    (setq str211 (polar str21 (+ ang (dtr 270)) (- flghd piphd)))
    (setq str2111 (polar str211 (+ ang (dtr 270)) pipd ))
    (setq str3  (polar str2 (+ ang (dtr 270)) flgd))
    (setq str31 (polar str3 (+ ang (dtr 180)) flgthk))
    (setq str4  (polar str1 (+ ang (dtr 270)) flgd))
    (setq str41 (polar str4 ang flgthk))
    (setq str5  (polar p2 ang (* flgd 0.6)))
    (setq str51 (polar str5 ang (* flgthk 0.5)))
    (setq str511(polar str51 ang (* flgthk 0.5)))
    (setq str512(polar str511 (+ ang (dtr 90)) (* flghd 1.3)))
    (setq str513(polar str511 (+ ang (dtr 270)) (* flghd 1.3)))
    (setq str6  (polar str5 (+ ang (dtr 270)) flghd))
    (setq str61 (polar str5 (+ ang (dtr 90)) flghd))
    (setq str62 (polar str511 (+ ang (dtr 270)) flghd))
    (setq str63 (polar str511 (+ ang (dtr 90)) flghd))
    (command "layer" "s" "2C" "")
    (command "pline" str1 "w" "0" "0" str11 str41 str4 str1 "c")
    (command "pline" str2 "w" "0" "0" str21 str31 str3 str2 "c")
    (command "line" str111 str211 "")
    (command "line" str1111 str2111 "")
    (command "line" str6 str62 "")
    (command "line" str61 str63 "")
    (command "layer" "s" "1E" "")
    (command "line" str512 str513 "")
    (command "insert" "*c:/ghk/dwg/flg45" str511 flghd ang1)
    (command "insert" "*c:/ghk/dwg/45dnd" str51 flghd ang1)
    (command "insert" "*c:/ghk/dwg/45dnd" str5 flghd ang1)
    (pse2)
)

(defun strset(/ p2sel)
    (pse1)
    (p-data3)
    (p-data4)
    (p-data5 "y-str")
    (endflgtype)
    (if (> vall 1)
        (progn
            (setvar "osmode" 512)
            (setq p1 (getpoint    "\nSelection point :[Default = nea point]:"))
            (setvar "osmode" 512)
            (setq p2 (getpoint p1 "\nSecond point    :[Default = nea point]:"))
            (setq p2sel(ssget p2))
            (setvar "osmode" 0)
            (setq ang (ANGLE P1  P2))
            (setq ang1 (rtd ang))
            (terpri)
            (prompt "Do you want flange to flange dimension < Default =")
            (princ vall)
            (prompt " > : ")
            (setq vall-1(getreal ""))
            (terpri)
            (if (= vall-1 nil)(setq vall vall)(setq vall vall-1))
            (if (or (= flg_end "F")(= flg_end "W")(= flg_end nil))
                (setq len (+ vall ga))
                (setq len vall)
            )
            (if (/= p2sel nil)
                (command "break" p1 "f" p2 (polar p2 ang len))
            )
            (command "layer" "s" "1E" "")
            (command "line" p2 (polar p2 ang len) "")
            (if (or (= flg_end "F") (= flg_end "W"))
                (progn
                    (if (not val-flg)(load"c:/ghk/lsp/val-flg"))
                    (val-flg ang p2)
                    (val-flg (+ ang (dtr 180)) (polar p2 ang len))
                )
            )
        )
        (prompt "\n    IS NOT SIZE")
    )
)
