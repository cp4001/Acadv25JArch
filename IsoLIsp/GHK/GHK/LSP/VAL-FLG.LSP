;<<<<<<<<<<<<<<<<<<<<<<<<<<< Valve Flange Variable >>>>>>>>>>>>>>>>>>>>>>>
;;;;;;;;;;;;;;;ang  p2
(defun val-flg(val1 val2 / p21 p211 p22 p221 p3 p311 p321 p31 p32 p4 p41
                           p42 p43 p44 p5 p51 p52 p4sel)
    (if (or (= sd "W") (= sd "S"))
        (progn
            (setq p21 (polar val2 (+ val1 (dtr 90)) flghd))
            (setq p22 (polar val2 (+ val1 (dtr 270)) flghd))
            (setq p211 (polar val2 (+ val1 (dtr 90)) (/ hubdia 2)))
            (setq p221 (polar val2 (+ val1 (dtr 270)) (/ hubdia 2)))
            (setq p3 (polar val2 (+ val1 (dtr 180)) flgthk))
            (setq p311 (polar p3 (+ val1 (dtr 90)) (/ hubdia 2)))
            (setq p321 (polar p3 (+ val1 (dtr 270)) (/ hubdia 2)))
            (setq p31 (polar p3 (+ val1 (dtr 90)) flghd))
            (setq p32 (polar p3 (+ val1 (dtr 270)) flghd))
            (setq p4 (polar val2 (+ val1 (dtr 180)) flglen))
            (minpipe)
            (if (= sd "S")
                (progn
                    (setq p41 (polar p4 (+ val1 (dtr 90)) (/ hubdia 2)))
                    (setq p42 (polar p4 (+ val1 (dtr 270)) (/ hubdia 2)))
                    (setq p43 (polar p4 (+ val1 (dtr 90)) piphd))
                    (setq p44 (polar p4 (+ val1 (dtr 270)) piphd))
                    (setq p5  (polar val2 (+ val1 (dtr 180)) (+ flglen minpip)))
                    (setq p51 (polar p5 (+ val1 (dtr 90)) piphd))
                    (setq p52 (polar p5 (+ val1 (dtr 270)) piphd))
                )
                (progn
                    (setq p41 (polar p4 (+ val1 (dtr 90)) piphd))
                    (setq p42 (polar p4 (+ val1 (dtr 270)) piphd))
                )
            )
;            (if (or (= flg-type 0) (>= ghk double))
            (if (and (= flg-type 0) (< ghk double))
                (progn
                    (setq p4sel(ssget (polar p4 val1 (* s 5))))
                    (if (/= p4sel nil)
                        (command "break" val2 p4)
                    )
                    (command "layer" "s" "1E" "")
                    (command "line" val2 p4 "")
                )
            )
        )
    )
;<<<<<<<<<<<<<<<<<<<<<< valve flange line dwg >>>>>>>>>>>>>>>>>>>>>>>>>>>>
    (ls1)
    (if (= sd "W")
        (cond
            ((< ghk double)
                (if (= flg-type 0)
                    (command "pline" p311 "w" "0" "0" p321 p4 p311 p31 p21 p22 p32 P321 "")
                    (progn
                        (command "line" p21 p22 "")
                        (command "layer" "s" "2C" "")
                        (command "solid" p211 p4 p221 p4 ^c)
                    )
                )
                (weld-mark p4)
            )
            ((>= ghk double)
                (command "pline" p311 "w" "0" "0" p321 p42 p41 p311 p31 p21 p22 p32 P321 "")
            )
        )
    )
    (if (= sd "S")
        (if (< ghk double)
            (if (= flg-type 0)
                (command "pline" p311 "w" "0" "0" p31 p21 p22 p32 P311 "")
                (command "line" p21 p22 "")
            )
            (command "pline" p311 "w" "0" "0" p321 p42 p41 p311 p31 p21 p22 p32 P321 "" "line" p43 p51 p52 p44 "")
        )
    )
;<<<<<<<<<<<<<<<<<<<<<<<<<<< Valve Flange Variable >>>>>>>>>>>>>>>>>>>>>>>
    (if (= sd "L")
        (progn
            (setq p21  (polar val2 (+ val1 (dtr 90)) (/ stubd 2)))
            (setq p211 (polar p21(+ val1 (dtr 180)) flgthk))
            (setq p22  (polar val2 (+ val1 (dtr 270)) (/ stubd 2)))
            (setq p221 (polar p22(+ val1 (dtr 180)) flgthk))
            (setq p3   (polar val2 (+ val1 (dtr 180)) flgthk))
            (setq p31  (polar p3 (+ val1 (dtr 90)) flghd))
            (setq p311 (polar p3 (+ val1 (dtr 90)) g))
            (setq p32  (polar p3 (+ val1 (dtr 270)) flghd))
            (setq p321 (polar p3 (+ val1 (dtr 270)) g))
            (setq p5   (polar p3 (+ val1 (dtr 180)) flgthk))
            (setq p51  (polar p5 (+ val1 (dtr 90)) flghd))
            (setq p52  (polar p5 (+ val1 (dtr 270)) flghd))
            (setq p43  (polar p5 (+ val1 (dtr 270)) piphd))
            (setq p44  (polar p5 (+ val1 (dtr 90)) piphd))
            (setq p4   (polar val2 (+ val1 (dtr 180)) stubl))
            (setq p41  (polar p4 (+ val1 (dtr 270)) piphd))
            (setq p42  (polar p4 (+ val1 (dtr 90)) piphd))
;            (if (or (= flg-type 0) (>= ghk double))
            (if (and (= flg-type 0) (< ghk double))
                (progn
                    (setq p4sel(ssget (polar p4 val1 (* s 5))))
                    (if (/= p4sel nil)
                        (command "break" val2 p4)
                    )
                    (command "layer" "s" "1E" "")
                    (command "line" val2 p4 "")
                )
            )
;<<<<<<<<<<<<<<<<<<<<<< valve flange line dwg >>>>>>>>>>>>>>>>>>>>>>>>>>>>
            (ls1)
            (if (< ghk double)
                (if (= flg-type 0)
                    (progn
                        (command "pline" p211 "w" "0" "0" p21 p22 p221 "")
                        (command "pline" p31 "w" "0" "0" p32 p52 p51 p31 "")
                        (weld-mark p4)
                    )
                    (progn
                        (command "line" p21 p22 "")
                        (command "line" p31 p311 "")
                        (command "line" p32 p321 "")
                        (weld-mark p4)
                    )
                )
                (progn
                    (command "pline" p211 "w" "0" "0" p21 p22 p221 "")
                    (command "pline" p31 "w" "0" "0" p32 p52 p51 p31 "")
                    (command "line" p44 p42 p41 p43 "")
                )
            )
        )
    )
)
;<<<<<<<<< Valve Flange Variable End >>>>>>>>>>>>>>>>>>>>>>>
