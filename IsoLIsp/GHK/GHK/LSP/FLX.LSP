;;;;;;;flexible tube lisp ( A-13 )
(defun flx(/ a-pip k-pip flglen flgd flgthk hubdia flghd stubl p2sel
             stubl1 stubd vall len p1 p2 ang vall-1)
    (pse1)
    (p-data3)
    (p-data4)
    (endflgtype)
    (setvar "osmode" 512)
    (setq p1 (getpoint    "\nSelection point :[Default = nea point]:"))
    (setvar "osmode" 512)
    (setq p2 (getpoint p1 "\nSecond point    :[Default = nea point]:"))
    (setq p2sel(ssget p2))
    (setq ang (angle p1 p2))
    (if (< ghk 50)
        (setq vall 200)
        (if (< ghk 150)
            (setq vall 300)
            (setq vall 400)
        )
    )
    (terpri)
    (prompt "Do you want flange to flange dimension < Default =")
    (princ vall)
    (prompt " > : ")
    (setq vall-1(getreal ""))
    (terpri)
    (if (= vall-1 nil)(setq vall vall)(setq vall vall-1))
    (if (or (= flg_end "F")(= flg_end "W")(= flg_end nil))
        (setq len (+ vall ga))
        (setq len vall)
    )
    (if (/= p2sel nil)
        (command "break" p2 (polar p2 ang len))
    )
    (command "layer" "s" "1E" "")
    (command "line" p2 (polar p2 ang len) "")
    (if (or (= flg_end "F") (= flg_end "W"))
        (progn
            (if (not val-flg)(load"c:/ghk/lsp/val-flg"))
            (val-flg ang p2)
            (val-flg (+ ang (dtr 180)) (polar p2 ang len))
        )
    )
    (flxbase ang p2)
    (pse2)
);;;;;;;;;;;;;;ang      p2
(defun flxbase(val-par1 val-par2 / flx1 flx1a flx1b flx2 flx2a flx2b flx2c
               flx2d flx3 flx3a flx3b flx4 flx4a flx4b flx4c flx4d)
    (setvar "osmode" 0)
    (setq flx1  (polar val-par2 val-par1 g))
    (setq flx1a (polar flx1 (+ val-par1 (dtr 90)) flghd))
    (setq flx1b (polar flx1 (+ val-par1 (dtr 270)) flghd))
    (setq flx2  (polar flx1 val-par1 flgthk))
    (setq flx2a (polar flx2 (+ val-par1 (dtr 90)) flghd))
    (setq flx2b (polar flx2 (+ val-par1 (dtr 270)) flghd))
    (setq flx2c (polar flx2 (+ val-par1 (dtr 90)) piphd))
    (setq flx2d (polar flx2 (+ val-par1 (dtr 270)) piphd))
    (setq flx3  (polar flx1 val-par1 (- len (* g 2))))
    (setq flx3a (polar flx3 (+ val-par1 (dtr 90)) flghd))
    (setq flx3b (polar flx3 (+ val-par1 (dtr 270)) flghd))
    (setq flx4  (polar flx3 (+ val-par1 (dtr 180)) flgthk))
    (setq flx4a (polar flx4 (+ val-par1 (dtr 90)) flghd))
    (setq flx4b (polar flx4 (+ val-par1 (dtr 270)) flghd))
    (setq flx4c (polar flx4 (+ val-par1 (dtr 90)) piphd))
    (setq flx4d (polar flx4 (+ val-par1 (dtr 270)) piphd))
    (command "layer" "s" "1C" "")
    (command "pline" flx2c "w" "0" "0" flx2d flx4d flx4c "c")
    (command "hatch" "ansi37" (* s 10) "0" "l" "")
    (command "erase" "p" "")
    (command "layer" "s" "2C" "")
    (command "pline" flx2d "w" "0" "0" flx2a flx1a flx1b flx2b flx2d
    flx4d flx4a flx3a flx3b flx4b flx4c flx2c "")
)
