;;;;;; flow mark
(defun flow(/ os sp p1 p2 ang)
    (setq os (getvar "osmode"))
    (setq sp (getvar "snapmode"))
    (setvar "snapmode" 1)
    (setvar "osmode" 512)
    (setq p1 (getpoint "Insert point :"))(print)
    (setvar "osmode" 512)
    (setq p2 (getpoint p1 "Seccond point :"))(print)
    (setvar "osmode" 0)
    (setq ang (angle p1 p2))
    (setq ang (rtd ang))
    (command "insert" "c:/ghk/dwg/flowmark" p1 s s ang)
    (setvar "snapmode" sp)
    (setvar "osmode" os)
)
;<<<<<<<<<<<<<<<<<<<<<<<<<<<<<<<<<<<<<<<<<<<<<<<<<<
;;;;;; ti mark
(defun ti(/ os p1 p2 ang)
    (setq os (getvar "osmode"))
    (setvar "osmode" 512)
    (setq p1 (getpoint "Insert point :"))(print)
    (setvar "osmode" 512)
    (setq p2 (getpoint p1 "Seccond point :"))(print)
    (setvar "osmode" 0)
    (setq ang (angle p1 p2))
    (setq ang (rtd ang))
    (command "insert" "*c:/ghk/dwg/ti" p1 s ang)
    (setvar "osmode" os)
)
;<<<<<<<<<<<<<<<<<<<<<<<<<<<<<<<<<<<<<<<<<<<<<<<<<<
;;;;;; slope mark
(defun slop(/ os p1 p2 ang)
    (setq os (getvar "osmode"))
    (setvar "osmode" 512)
    (setq p1 (getpoint "Insert point :"))(print)
    (setvar "osmode" 512)
    (setq p2 (getpoint p1 "Seccond point :"))(print)
    (setvar "osmode" 0)
    (setq ang (angle p1 p2))
    (setq ang (rtd ang))
    (command "insert" "*c:/ghk/dwg/slop" p1 s ang)
    (setvar "osmode" os)
)
;<<<<<<<<<<<<<<<<<<<<<<<<<<<<<<<<<<<<<<<<<<<<<<<<<<
;;;;;; sol vant
(defun sol(/ os p1 p2 ang)
    (setq os (getvar "osmode"))
    (setvar "osmode" 32)
    (setq p1 (getpoint "Insert point :"))(print)
    (setvar "osmode" 512)
    (setq p2 (getpoint p1 "Seccond point :"))(print)
    (setvar "osmode" 0)
    (setq ang (angle p1 p2))
    (setq ang (rtd ang))
    (command "insert" "*c:/ghk/dwg/sol" p1 s ang)
    (setvar "osmode" os)
)
;<<<<<<<<<<<<<<<<<<<<<<<<<<<<<<<<<<<<<<<<<<<<<<<<<<
;;;;;; ladder mark
(defun ladder(/ p1 p2 ang)
    (setq p1 (getpoint "Insert point :"))(print)
    (setq p2 (getpoint p1 "Seccond point :"))(print)
    (setq ang (angle p1 p2))
    (setq ang (rtd ang))
    (command "insert" "*c:/ghk/dwg/ladder" p1 "1" ang)
)
;<<<<<<<<<<<<<<<<<<<<<<<<<<<<<<<<<<<<<<<<<<<<<<<<<<
;;;;;; Revised mark
(defun rev(/ p1 p3 p4 p5 p6 txt1)
    (se3)
    (setq p1 (getpoint  "\nInsert point : "))
    (if (not txt)(setq txt "A"))
    (prompt "Revision No. : < ")
    (princ txt)
    (prompt " > : ")
    (setq txt1(getstring " "))
    (terpri)
    (if (or (= txt1 "")(= txt1 nil))(setq txt txt)(setq txt txt1))
    (setvar "osmode" 0)
    (setq p3 (polar p1 (dtr 90)  (* s 3)))
    (setq p4 (polar p1 (dtr 270) (* s 4)))
    (setq p5 (polar p4 (dtr 0)   (* s 4)))
    (setq p6 (polar p4 (dtr 180) (* s 4)))
    (command "layer" "s" "rev" "")
    (c:lst1)
    (command "pline" p3 "w" "0" "0" p5 p6 "c")
    (command "text" "j" "tc" p1 (* s 2.5) "0" txt)
    (command "move" (ss-add) "" p1 pause)
    (se6)
)
;<<<<<<<<<<<<<<<<<<<<<<<<<<<<<<<<<<<<<<<<<<<<<<<<<<
;;;;;; detail mark1
(defun detail1(/ p1 p2 ang)
    (setq p1 (getpoint "Insert point :"))(print)
    (setq p2 (getpoint p1 "Seccond point :"))(print)
    (setq ang (angle p1 p2))
    (setq ang (rtd ang))
    (command "insert" "*c:/ghk/dwg/detail1" p1 s ang)
)
;<<<<<<<<<<<<<<<<<<<<<<<<<<<<<<<<<<<<<<<<<<<<<<<<<<
;;;;;; detail mark2
(defun detail2(/ p1 p2 ang)
    (setq p1 (getpoint "Insert point :"))(print)
    (setq p2 (getpoint p1 "Seccond point :"))(print)
    (setq ang (angle p1 p2))
    (setq ang (rtd ang))
    (command "insert" "*c:/ghk/dwg/detail2" p1 s ang)
)
;<<<<<<<<<<<<<<<<<<<<<<<<<<<<<<<<<<<<<<<<<<<<<<<<<<
;;;;;; detail mark3
(defun detail3(/ p1 p2 ang)
    (setq p1 (getpoint "Insert point :"))(print)
    (setq p2 (getpoint p1 "Seccond point :"))(print)
    (setq ang (angle p1 p2))
    (setq ang (rtd ang))
    (command "insert" "*c:/ghk/dwg/detail3" p1 s ang)
)
;<<<<<<<<<<<<<<<<<<<<<<<<<<<<<<<<<<<<<<<<<<<<<<<<<<
;;;;;; detail mark4
(defun detail4(/ p1 p2 ang)
    (setq p1 (getpoint "Insert point :"))(print)
    (setq p2 (getpoint p1 "Seccond point :"))(print)
    (setq ang (angle p1 p2))
    (setq ang (rtd ang))
    (command "insert" "*c:/ghk/dwg/detail4" p1 s ang)
)
;<<<<<<<<<<<<<<<<<<<<<<<<<<<<<<<<<<<<<<<<<<<<<<<<<<
;;;;;; detail mark5
(defun detail5(/ p1 p2 ang)
    (setq p1 (getpoint "Insert point :"))(print)
    (setq p2 (getpoint p1 "Seccond point :"))(print)
    (setq ang (angle p1 p2))
    (setq ang (rtd ang))
    (command "insert" "*c:/ghk/dwg/detail5" p1 s ang)
)
;<<<<<<<<<<<<<<<<<<<<<<<<<<<<<<<<<<<<<<<<<<<<<<<<<<
;;;;;; detail mark6
(defun detail6(/ p1 p2 ang)
    (setq p1 (getpoint "Insert point :"))(print)
    (setq p2 (getpoint p1 "Seccond point :"))(print)
    (setq ang (angle p1 p2))
    (setq ang (rtd ang))
    (command "insert" "*c:/ghk/dwg/detail6" p1 s ang)
)
;<<<<<<<<<<<<<<<<<<<<<<<<<<<<<<<<<<<<<<<<<<<<<<<<<<
;;;;;; detail mark7
(defun detail7(/ p1 p2 ang)
    (setq p1 (getpoint "Insert point :"))(print)
    (setq p2 (getpoint p1 "Seccond point :"))(print)
    (setq ang (angle p1 p2))
    (setq ang (rtd ang))
    (command "insert" "*c:/ghk/dwg/detail7" p1 s ang)
)
;<<<<<<<<<<<<<<<<<<<<<<<<<<<<<<<<<<<<<<<<<<<<<<<<<<
;;;;;; detail mark8
(defun detail8(/ p1 p2 ang)
    (setq p1 (getpoint "Insert point :"))(print)
    (setq p2 (getpoint p1 "Seccond point :"))(print)
    (setq ang (angle p1 p2))
    (setq ang (rtd ang))
    (command "insert" "*c:/ghk/dwg/detail8" p1 s ang)
)
;<<<<<<<<<<<<<<<<<<<<<<<<<<<<<<<<<<<<<<<<<<<<<<<<<<
;;;;;; section mark
(defun section(/ p1 p2 ang)
    (setq p1 (getpoint "Insert point :"))(print)
    (setq p2 (getpoint p1 "Seccond point :"))(print)
    (setq ang (angle p1 p2))
    (setq ang (rtd ang))
    (command "insert" "*c:/ghk/dwg/section" p1 s ang)
)
;<<<<<<<<<<<<<<<<<<<<<<<<<<<<<<<<<<<<<<<<<<<<<<<<<<
;;;;;; section mark
(defun section1(/ p1 p2 ang)
    (setq p1 (getpoint "Insert point :"))(print)
    (setq p2 (getpoint p1 "Seccond point :"))(print)
    (setq ang (angle p1 p2))
    (setq ang (rtd ang))
    (command "insert" "*c:/ghk/dwg/section1" p1 s ang)
)
;<<<<<<<<<<<<<<<<<<<<<<<<<<<<<<<<<<<<<<<<<<<<<<<<<<
;;;;;; section text
(defun sec-text(/ p1 p2 ang)
    (setq p1 (getpoint "Insert point :"))(print)
    (setq p2 (getpoint p1 "Seccond point :"))(print)
    (setq ang (angle p1 p2))
    (setq ang (rtd ang))
    (command "insert" "*c:/ghk/dwg/sec-text" p1 s ang)
)
;<<<<<<<<<<<<<<<<<<<<<<<<<<<<<<<<<<<<<<<<<<<<<<<<<<
;;;;;; section text
(defun sect1(/ p1 p2 ang)
    (setq p1 (getpoint "Insert point :"))(print)
    (setq p2 (getpoint p1 "Seccond point :"))(print)
    (setq ang (angle p1 p2))
    (setq ang (rtd ang))
    (command "insert" "*c:/ghk/dwg/sect1" p1 s ang)
)
;<<<<<<<<<<<<<<<<<<<<<<<<<<<<<<<<<<<<<<<<<<<<<<<<<<
;;;;;; section text
(defun sect2(/ p1 p2 ang)
    (setq p1 (getpoint "Insert point :"))(print)
    (setq p2 (getpoint p1 "Seccond point :"))(print)
    (setq ang (angle p1 p2))
    (setq ang (rtd ang))
    (command "insert" "*c:/ghk/dwg/sect2" p1 s ang)
)
;<<<<<<<<<<<<<<<<<<<<<<<<<<<<<<<<<<<<<<<<<<<<<<<<<<
;;;;;; section text
(defun sect3(/ p1 p2 ang)
    (setq p1 (getpoint "Insert point :"))(print)
    (setq p2 (getpoint p1 "Seccond point :"))(print)
    (setq ang (angle p1 p2))
    (setq ang (rtd ang))
    (command "insert" "*c:/ghk/dwg/sect3" p1 s ang)
)
;<<<<<<<<<<<<<<<<<<<<<<<<<<<<<<<<<<<<<<<<<<<<<<<<<<
;;;;;; section text
(defun sect(/ p1 p2 ang)
    (setq p1 (getpoint "Insert point :"))(print)
    (setq p2 (getpoint p1 "Seccond point :"))(print)
    (setq ang (angle p1 p2))
    (setq ang (rtd ang))
    (command "insert" "*c:/ghk/dwg/sect" p1 s ang)
)
;<<<<<<<<<<<<<<<<<<<<<<<<<<<<<<<<<<<<<<<<<<<<<<<<<<
;;;;;; Lucky north mark
(defun lnorth(/ os p1 p2 cird txt1 txt2 ang angb angc a1 a2 a3 p3 p4 p5
                p6 p7 p8 p9 t1 t2 t3 t4 t5 t6 t7 t8 t9 t10 t11 t12 t13
                t14 t15 t16 t17 t18 t19 t20)
    (setq os (getvar "osmode"))
    (setq p1 (getpoint "Inset point:"))
    (setq p2 (getpoint p1 "Direction :"))
    (setvar "osmode" 0)
    (setq cird (* s 20))
    (setq txt1 (* s 2.5))
    (setq txt2 (* s 4))
    (SETQ ang (ANGLE P1 P2))
    (setq angb (+ ang 2.19911))
    (setq angc (- ang 2.19911))
    (setq a1 (- ang 3.14159))
    (setq a2 (+ ang 1.5708))
    (setq a3 (- ang 1.5708))
    (setq p3 (polar p1 a3 (/ cird 2)))
    (setq p4 (polar p1 a2 (/ cird 2)))
    (setq p5 (polar p1 ang (/ cird 2)))
    (setq p6 (polar p1 a1 (/ cird 2)))
    (setq p7 (polar p1 a1 (/ cird 4)))
    (setq p8 (polar p7 angb (* s 6.1965)))
    (setq p9 (polar p7 angc (* s 6.1965)))
    (setq t1 (polar p3 a3 (/ cird 20)))
    (setq t2 (polar p4 a2 (/ cird 20)))
    (setq t3 (polar p5 ang (/ cird 20)))
    (setq t4 (polar p6 a1 (/ cird 20)))
    (setq t5 (polar p1 ang (* cird 0.8)))
    (setq t6 (polar p3 a3 (/ cird 20)))
    (setq t7 (polar p4 a2 (/ cird 20)))
    (setq t8 (polar p5 ang (/ cird 20)))
    (setq t9 (polar p6 a1 (/ cird 20)))
    (setq t10(polar p1 ang (* cird 0.8)))
    (setq t11(polar p3 a3 (/ cird 20)))
    (setq t12(polar p4 a2 (/ cird 20)))
    (setq t13(polar p5 ang (/ cird 20)))
    (setq t14(polar p6 a1 (/ cird 20)))
    (setq t15(polar p1 ang (* cird 0.8)))
    (setq t16(polar p3 a3 (/ cird 20)))
    (setq t17(polar p4 a2 (/ cird 20)))
    (setq t18(polar p5 ang (/ cird 20)))
    (setq t19(polar p6 a1 (/ cird 20)))
    (setq t20(polar p1 ang (* cird 0.8)))
    (command "layer" "s" "5C" "")
    (command "circle" p1 "d" cird)
    (command "pline" p5 "w" "0" "0" p9 p7 p8 p5 "")
    (command "solid" p5 p7 p8 p7 ^c)
    (if (= ang 0)
        (progn
         (command "text" "j" "tc" t1 txt1 "0" "90%%d")
         (command "text" "j" "c" t2 txt1 "0" "270%%d")
         (command "text" "j" "ml" t3 txt1 "0" "0%%d")
         (command "text" "j" "mr" t4 txt1 "0" "180%%d")
         (command "text" "j" "ml" t5 txt2 "0" "PN")
        )
    )
    (if (= (rtd ang) 90)
        (progn
         (command "text" "j" "ml" t6 txt1 "0" "90%%d")
         (command "text" "j" "mr" t7 txt1 "0" "270%%d")
         (command "text" "j" "c" t8 txt1 "0" "0%%d")
         (command "text" "j" "tc" t9 txt1 "0" "180%%d")
         (command "text" "j" "c" t10 txt2 "0" "PN")
        )
    )
    (if (= (rtd ang) 180)
        (progn
         (command "text" "j" "c" t11 txt1 "0" "90%%d")
         (command "text" "j" "tc" t12 txt1 "0" "270%%d")
         (command "text" "j" "mr" t13 txt1 "0" "0%%d")
         (command "text" "j" "ml" t14 txt1 "0" "180%%d")
         (command "text" "j" "mr" t15 txt2 "0" "PN")
        )
    )
    (if (= (rtd ang) 270)
       (progn
         (command "text" "j" "mr" t16 txt1 "0" "90%%d")
         (command "text" "j" "ml" t17 txt1 "0" "270%%d")
         (command "text" "j" "tc" t18 txt1 "0" "0%%d")
         (command "text" "j" "c" t19 txt1 "0" "180%%d")
         (command "text" "j" "tc" t20 txt2 "0" "PN")
       )
    )
    (command "layer" "s" "1E" "")
    (command "line" p4 p3 "")
    (command "layer" "s" la "")
    (setvar "osmode" os)
    (prin1)
)
;<<<<<<<<<<<<<<<<<<<<<<<<<<<<<<<<<<<<<<<<<<<<<<<<<<
;;;;;;section down straight tee lisp
(defun drain(/ os p1 p2 piphd flghd ang a1 a2 a3 a4 a5 a6 a7 p3 p4 p5 p6
               p7 p8 p9 p10 p11 p12 la)
    (setq os (getvar "osmode"))
    (setvar "osmode" 512)
    (setq p1 (getpoint "Tee center point [Default = nea point]:"))(terpri)
    (setvar "osmode" 512)
    (setq p2 (getpoint p1 "Select pipe line [Defaulut = nea point]:"))
    (setvar "osmode" 0)
    (IF (= S 30)
        (progn
        (setq piphd 13.7)
        (setq flghd 49.5)
        )
     )
    (IF (= S 50)
        (progn
        (setq piphd 24.1)
        (setq flghd 63.5)
        )
     )
    (IF (= S 100)
        (progn
        (setq piphd 44.5)
        (setq flghd 195.0)
        )
     )
    (SETQ ang (ANGLE P1  P2))
    (setq a1 (- ang (dtr 180)))
    (setq a2 (+ ang (dtr 90)))
    (setq a3 (- ang (dtr 90)))
    (setq a4 (+ ang (dtr 30)))
    (setq a5 (- ang (dtr 30)))
    (setq a6 (+ ang (dtr 150)))
    (setq a7 (- ang (dtr 150)))
    (setq p3 (polar p1 a4 piphd))
    (setq p4 (polar p1 a5 piphd))
    (setq p5 (polar p1 a6 piphd))
    (setq p6 (polar p1 a7 piphd))
    (setq p7 (polar p1 a4 flghd))
    (setq p8 (polar p1 a5 flghd))
    (setq p9 (polar p1 a6 flghd))
    (setq p10(polar p1 a7 flghd))
    (setq p11(polar p1 a2 (* flghd 1.3)))
    (setq p12(polar p1 a3 (* flghd 1.3)))
    (setq la (getvar "clayer"))
    (command "layer" "s" "3C" "")
    (command "arc" "c" p1 p3 p5)
    (command "arc" "c" p1 p6 p4)
    (command "arc" "c" p1 p7 p9)
    (command "arc" "c" p1 p10 p8)
    (command "layer" "s" "1E" "")
    (command "line" p11 p12 "")
    (command "layer" "s" la "")
    (setvar "osmode" os)
    (prin1)
)
;;;;;;section vent straight tee lisp
(defun vent(/ os p1 p2 piphd flghd ang a1 a2 a3 p3 p4 p5 p6
               p7 p8 la)
    (setq os (getvar "osmode"))
    (setvar "osmode" 512)
    (setq p1 (getpoint "Tee center point [Default = nea point]:"))(terpri)
    (setvar "osmode" 512)
    (setq p2 (getpoint p1 "Select pipe line [Defaulut = nea point]:"))
    (setvar "osmode" 0)
    (IF (= S 30)
        (progn
        (setq piphd 13.7)
        (setq flghd 49.5)
        )
     )
    (IF (= S 50)
        (progn
        (setq piphd 24.1)
        (setq flghd 63.5)
        )
     )
    (IF (= S 100)
        (progn
        (setq piphd 44.5)
        (setq flghd 195.0)
        )
     )
    (SETQ ang (ANGLE P1  P2))
    (setq a1 (- ang (dtr 180)))
    (setq a2 (+ ang (dtr 90)))
    (setq a3 (- ang (dtr 90)))
    (setq p3 (polar p1 ang piphd))
    (setq p4 (polar p1 a1 piphd))
    (setq p5 (polar p1 ang flghd))
    (setq p6 (polar p1 a1 flghd))
    (setq p7 (polar p1 a2 (* flghd 1.3)))
    (setq p8 (polar p1 a3 (* flghd 1.3)))
    (setq la (getvar "clayer"))
    (command "break" p1 "f" p5 p6 "")
    (command "layer" "s" "2C" "")
    (command "circle" p1 p3)
    (command "circle" p1 p5)
    (command "layer" "s" "1E" "")
    (command "line" p5 p6 "")
    (command "line" p7 p8 "")
    (command "layer" "s" la "")
    (setvar "osmode" os)
    (prin1)
)
