;<<<<<<<<<<<<<<<<<<<<<<<< AUTO CAD LISP >>>>>>>>>>>>>>>>>>>>>>>>>>>>>>>
;~~~~~~~~~~~~~~~~~~~~~~~~CHECK VALVE SIDE LISP~~~~~~~~~~~~~~~~~~~~~~~~~~
(defun chkvf(/ a-pip k-pip flglen flgd flgthk hubdia flghd stubl p2sel
               stubl1 stubd vall vall1 vall2 len p1 p2 ang)
    (if (/= job_direc 1)
        (pse1)
    )
    (p-data3)
    (p-data4)
    (p-data5 "chev")
    (if (> vall 1)
        (progn
            (endflgtype)
            (if (= job_direc 1)
                (progn
                    (setq p2 endpoint)
                    (setq ang endang)
                    (setq p2sel(ssget p2))
                )
                (progn
                    (setvar "osmode" 512)
                    (setq p1 (getpoint    "\nSelection point :[Default = nea point]:"))
                    (setvar "osmode" 512)
                    (setq p2 (getpoint p1 "\nSecond point    :[Default = nea point]:"))
                    (setq p2sel(ssget p2))
                    (setvar "osmode" 0)
                    (setq ang (angle p1 p2))
                )
            )
            (if (/= p2sel nil)
                (command "break" p2 (polar p2 ang len))
            )
            (command "layer" "s" "1E" "")
            (command "line" p2 (polar p2 ang len) "")
            (if (or (= flg_end "F") (= flg_end "W"))
                (progn
                    (if (not val-flg)(load"c:/ghk/lsp/val-flg"))
                    (val-flg ang p2)
                    (val-flg (+ ang (dtr 180)) (polar p2 ang len))
                )
            )
            (checkbase ang p2 p1)
        )
        (prompt "\n    IS NOT SIZE")
    )
    (if (/= job_direc 1)
        (pse2)
    )
)

(defun checkbase(che-par1 che-par2 che-par3 / val_1 val_2 val1 val2 val3
                  val4 val5 val6)
    (if (not valve)(load"c:/ghk/lsp/valve"))
    (valve che-par1 che-par2)
    (setq val5 (polar val4 (+ che-par1 (dtr 270)) (/ piphd 4)))
    (setq val6 (polar val3 (+ che-par1 (dtr 270)) (/ piphd 4)))
    (command "layer" "s" "2C" "")
    (command "pline" val4 "w" "0" "0" val1 val3 val2 "")
    (setq asz (getvar "dimasz"))
    (cond
        ((< ghk 40)
            (setvar "dimasz" 1)
            (command "dim" "lea" val6 val5 ^c "e")
        )
        ((< ghk 100)
            (setvar "dimasz" 1.5)
            (command "dim" "lea" val6 val5 ^c "e")
        )
        ((< ghk 300)
            (setvar "dimasz" 2)
            (command "dim" "lea" val6 val5 ^c "e")
        )
        ((> ghk 300)
            (setvar "dimasz" 2.5)
            (command "dim" "lea" val6 val5 ^c "e")
        )
    )
)
