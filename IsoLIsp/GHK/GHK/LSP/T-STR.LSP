;<<<<<<<<<<<<<<<<<<<<<<<< AUTO CAD LISP >>>>>>>>>>>>>>>>>>>>>>>>>>>>>>>
;~~~~~~~~~~~~~~~~T-TYPE STRAINER (WELD NECK) SIDE LISP~~~~~~~~~~~~~~~~~
(defun t-strf (/ la orth os a-pip k-pip flglen flgd flghd flgthk hubdia
                 stubl stubl1 stubd vall vall1 vall2 len p1 pp pp1 ang ang1
                 vall-1)
    (strset)
    (pse2)
)
;<<<<<<<<<<<<<<<<<<< strainer dwg>>>>>>>>>>>>>>>>>>>>>>>>>>>>>>>>>>>>>>>>>
(defun t-strain(/ s1 s1a s11 s2 s2a s2b s21 s22 s3 s3a s31 s4 s4a s4a1
                  s4a2 s4b s4b1 s4b2 s4b3 s4b4 s4c s4c1 s4c2 s5 s5a s6
                  s6a st1 st1a st11 st2 st2a st2b st21 st22 st3 st3a st31
                  st4 st4a st41 st5 st5a st51 sfcen1 sfcen2 sb1 sb1a
                  sb11 sb4a sb4a1 sb4a2)
    (setq s1   (polar p1 (+ ang (dtr 180)) (- len (+ (/ ga 2) g))))
    (setq s1a  (polar s1 ang1 flghd))
    (setq s11  (polar s1 (+ ang1 (dtr 180)) flghd))
    (setq s2   (polar s1 ang flgthk))
    (setq s2a  (polar s1a ang flgthk))
    (setq s2b  (polar s2 ang1 (/ hubdia 2)))
    (setq s21  (polar s11 ang flgthk))
    (setq s22  (polar s2 (+ ang1 (dtr 180)) (/ hubdia 2)))
    (setq s3   (polar s1 ang flglen))
    (setq s3a  (polar s3 ang1 piphd))
    (setq s31  (polar s3 (+ ang1 (dtr 180)) piphd))
    (setq s4   p1)
    (setq s4a  (polar s4  ang1 (- (+ vall2 (/ ga 2)) g)))
    (setq s4a1 (polar s4a (+ ang (dtr 180)) flghd))
    (setq s4a2 (polar s4a ang flghd))
    (setq s4b  (polar s4a (+ ang1 (dtr 180)) flgthk))
    (setq s4b1 (polar s4b (+ ang (dtr 180)) flghd))
    (setq s4b2 (polar s4b ang flghd))
    (setq s4b3 (polar s4b (+ ang (dtr 180)) (/ hubdia 2)))
    (setq s4b4 (polar s4b ang (/ hubdia 2)))
    (setq s4c  (polar s4a (+ ang1 (dtr 180)) flglen))
    (setq s4c1 (polar s4c (+ ang (dtr 180)) piphd))
    (setq s4c2 (polar s4c ang piphd))
    (setq s5    (polar s4 (+ ang (dtr 180)) piphd))
    (setq s5a   (polar s5 ang1 piphd))
    (setq s6    (polar s4 ang piphd))
    (setq s6a   (polar s6 ang1 piphd))
    (setq st1   (polar s4 ang (+ vall1 (/ ga 2))))
    (setq st1a  (polar st1 ang1 flghd))
    (setq st11  (polar st1 (+ ang1 (dtr 180)) flghd))
    (setq st2   (polar st1 (+ ang (dtr 180)) flgthk))
    (setq st2a  (polar st1a (+ ang (dtr 180)) flgthk))
    (setq st2b  (polar st2 ang1 (/ hubdia 2)))
    (setq st21  (polar st11 (+ ang (dtr 180)) flgthk))
    (setq st22  (polar st2 (+ ang1 (dtr 180)) (/ hubdia 2)))
    (setq st3   (polar st1 (+ ang (dtr 180)) flglen))
    (setq st3a  (polar st3 ang1 piphd))
    (setq st31  (polar st3 (+ ang1 (dtr 180)) piphd))
    (setq st4   (polar st1 ang flgthk))
    (setq st4a  (polar st1a ang flgthk))
    (setq st41  (polar st11 ang flgthk))
    (setq st5   (polar st4 ang (* len 2)))
    (setq st5a  (polar st4a ang (* len 2)))
    (setq st51  (polar st41 ang (* len 2)))
    (setq sfcen1 (polar s4 (+ ang1 (dtr 180)) (* piphd 1.3)))
    (setq sfcen2 (polar st5 ang (* piphd 0.3)))
    (setq sb1  (polar p1 (+ ang (dtr 180)) vall))
    (setq sb1a (polar sb1 ang1 piphd))
    (setq sb11 (polar sb1 (+ ang1 (dtr 180)) piphd))
    (setq sb4a (polar s4  ang1 vall2))
    (setq sb4a1(polar sb4a (+ ang (dtr 180)) piphd))
    (setq sb4a2(polar sb4a ang piphd))
<<<<<<<<<<<<<<<<<<< strainer dwg>>>>>>>>>>>>>>>>>>>>>>>>>>>>>>>>>>>>>>>>>
    (command "layer" "s" "2C" "")
    (command "pline" st2b "w" "0" "0" st3a st31 st22 st2a st4a st41 st21 st22 "")
    (if (= flg_end "B")
        (progn
            (command "break" sb4a "f" sb4a sfcen1)
            (command "break" sb1 "f" sb1 sfcen2)
            (command "pline" st31 "w" "0" "0" sb11 sb1a s5a sb4a1 sb4a2 s6a st3a "")
            (command "line" st1a st11 "")
            (command "layer" "s" "1E" "")
            (command "line" sfcen1 sb4a "")
            (command "line" sfcen2 sb1 "")
            (weld-mark sb1)
            (weld-mark sb4a)
        )
        (progn
            (command "pline" s2b "w" "0" "0" s3a s31 s22 s2a s1a s11 s21 s22 "")
            (command "pline" s4b3 "w" "0" "0" s4c1 s4c2 s4b4 s4b1 s4a1 s4a2 s4b2 s4b4 "")
            (command "line" st1a st11 "")
            (command "line" s3a s5a s4c1 "")
            (command "line" st3a s6a s4c2 "")
            (command "line" s31 st31 "")
            (command "layer" "s" "1E" "")
            (command "line" sfcen1 (polar s4a ang1 g) "")
            (command "line" sfcen2 (polar s1 (+ ang (dtr 180)) g) "")
        )
    )
    (command "layer" "s" "1P" "")
    (command "pline" st51 "w" "0" "0" st4a st5a st41 st51 st5a st51 "")
)

(defun strset(/ ppsel pp1sel)
    (pse1)
    (p-data3)
    (p-data4)
    (p-data5 "t-str")
    (endflgtype)
    (if (> vall 1)
        (progn
            (setvar "osmode" 32)
            (setq p1 (getpoint    "\nSelection point :[Default = nea point]:"))
            (setvar "osmode" 0)
            (setq pp (getpoint p1 "\nMaintence Area Direction :"))
            (setq pp1(getpoint p1 "\nDischarge Direction      :"))
            (setq ang (ANGLE P1  Pp))
            (setq ang1(ANGLE P1  Pp1))
            (setq ppsel(ssget (polar p1 (+ ang (dtr 180)) (- len (/ ga 2)))))
            (setq pp1sel(ssget pp1))
            (terpri)
            (prompt "Do you want flange to flange dimension < Default =")
            (princ vall)
            (prompt " > : ")
            (setq vall-1(getreal ""))
            (terpri)
            (if (= vall-1 nil)(setq vall vall)(setq vall vall-1))
            (if (or (= flg_end "F")(= flg_end "W")(= flg_end nil))
                (setq len (+ vall ga))
                (setq len vall)
            )
            (if (/= ppsel nil)
                (command "break" (polar p1 (+ ang (dtr 180)) (- len (/ ga 2))) p1)
            )
            (if (/= pp1sel nil)
                (command "break" (polar p1 ang1 (+ vall2 (/ ga 2))) p1)
            )
            (if (/= flg_end "B")
                (progn
                    (if (not val-flg)(load"c:/ghk/lsp/val-flg"))
                    (val-flg ang (polar p1 (+ ang (dtr 180)) (- len (/ ga 2))))
                    (val-flg (+ ang1 (dtr 180)) (polar p1 ang1 (+ vall2 (/ ga 2))))
                )
            )
            (t-strain)
        )
        (prompt "\n    IS NOT SIZE")
    )
)
