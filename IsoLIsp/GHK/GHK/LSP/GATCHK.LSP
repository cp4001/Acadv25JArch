;;;;;;;gate + check valve lisp
(defun gatchkvf(/ a-pip k-pip flglen flgd flgthk hubdia flghd stubl p2sel
               stubl1 stubd vall vall1 vall2 len p1 p2 ang g_len c_len
               t_len)
    (pse1)
    (p-data3)
    (p-data4)
    (p-data5 "gatv")
    (setq g_len len)
    (p-data5 "chev")
    (setq c_len len)
    (setq t_len (- (+ g_len c_len)(/ ga 2)))
    (setq p2sel nil)
    (if (= val-view nil)(setq val-view 1))
    (if (not gatebase)(load"c:/ghk/lsp/gatvf"))
    (if (not checkbase)(load"c:/ghk/lsp/chkvf"))
    (if (> vall 1)
        (progn
            (endflgtype)
            (setvar "osmode" 512)
            (setq p1 (getpoint    "\nSelection point :[Default = nea point]:"))
            (setvar "osmode" 512)
            (setq p2 (getpoint p1 "\nStart point    :[Default = nea point]:"))
            (setq p2sel(ssget p2))
            (setvar "osmode" 0)
            (setq ang (angle p1 p2))
            (if (/= p2sel nil)
                (command "break" p2 (polar p2 ang t_len))
            )
            (command "layer" "s" "1E" "")
            (command "line" p2 (polar p2 ang t_len) "")
            (if (or (= vall1 nil) (< vall1 1))
                (progn
                    (setq vall1(* vall 2))
                    (setq vall2 vall)
                )
            )
            (setq len (+ g_len (/ g 2)))
            (setq valve-t 1)
            (gatebase ang p2 p1)
            (setq len (+ c_len (/ g 2)))
            (checkbase ang (polar p2 ang (- g_len (/ g 2))) p1)
            (if (or (= flg_end "F") (= flg_end "W"))
                (progn
                    (if (not val-flg)(load"c:/ghk/lsp/val-flg"))
                    (val-flg ang p2)
                    (val-flg (+ ang (dtr 180)) (polar p2 ang t_len))
                )
            )
        )
        (prompt "\n    IS NOT SIZE")
    )
    (pse2)
)
