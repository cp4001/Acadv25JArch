;;;;;;front straight tee lisp ( D-3 )
(defun fst(/ P1 P2 ANG)
    (pse1)
    (setvar "osmode" 33)
    (setq p1 (getpoint "\n     Tee center point:[Default = int point]:"))
    (setvar "osmode" 512)
    (setq p2 (getpoint p1 "\n     Select pipe line:[Default = nea point]:"))
    (SETQ ang (angle P1  P2))
    (fst1 ang p2 p1)
    (pse2)
);;;;;;;;;;;;ang   p2    p1
(defun fst1(tee-1 tee-2 tee-3 / p4 p41p 42 p5 p51 p52 p6 p61 p62)
    (setq tee-type 1)
    (setq ang tee-1)
    (setq p2  tee-2)
    (setq p1  tee-3)
    (p-data1)
    (p-data4)
    (sub_tee1 tee piphd)
    (sub_tee2 tee piphd)
    (setq tee-type nil)
    (setvar "osmode" 0)
    (if (= withval nil)
        (progn
            (endconn-flg p4 ang)
            (endconn-flg p5 (+ ang (dtr 180)))
            (endconn-flg p6 (+ ang (dtr 90)))
        )
        (progn
            (setq endang (getangle p1 "\n     Valve Direction : "))
            (cond
                ((= ang endang)
                    (endconn-val p4 endang)
                    (endconn-flg p5 (+ ang (dtr 180)))
                    (endconn-flg p6 (+ ang (dtr 90)))
                )
                ((= (+ ang (dtr 180)) endang)
                    (endconn-val p5 endang)
                    (endconn-flg p4 ang)
                    (endconn-flg p6 (+ ang (dtr 90)))
                )
                ((= (+ ang (dtr 90)) endang)
                    (endconn-val p6 endang)
                    (endconn-flg p4 ang)
                    (endconn-flg p5 (+ ang (dtr 180)))
                )
            )
        )
    )
)
;;;;;;front reducing tee lisp ( D-6 )
(defun frt(/ p1 p2 ang)
    (pse1)
    (setvar "osmode" 32)
    (setq p1 (getpoint "\n     Tee center point:[Default = int point]:"))
    (setvar "osmode" 512)
    (setq p2 (getpoint p1 "\n     Select pipe line:[Default = nea point]:"))
    (setvar "osmode" 0)
    (setq ang (angle P1  P2))
    (frt1 ang p2 p1)
    (pse2)
);;;;;;;;;;;ang   p2    p1
(defun frt1(tee-1 tee-2 tee-3 / rt piphd2 br-len br-dia br-ghk br-ghk1 p4 p41
            p42 p5  p51 p52 p6 p61 p62 endang)
    (setq tee-type 4)
    (setq ang tee-1)
    (setq p2  tee-2)
    (setq p1  tee-3)
    (p-data1)
    (redtee)
    (if (= ok 1)
        (progn
            (sub_tee1 tee piphd)
            (setq rt(atof br-len))
            (setq br-ghk1 ghk)
            (setq ghk br-ghk)
            (p-data1)
            (sub_tee2 rt piphd)
        )
    )
    (setq tee-type nil)
    (setvar "osmode" 0)
    (if (/= withval nil)
        (progn
            (setq endang (getangle tee-3 "\n     Valve Direction : "))
            (cond
                ((= ang endang)
                    (endconn-flg p6 (+ ang (dtr 90)))
                    (setq ghk br-ghk1)
                    (p-data4)
                    (endconn-flg p5 (+ ang (dtr 180)))
                    (endconn-val p4 endang)
                )
                ((= (+ ang (dtr 180)) endang)
                    (endconn-flg p6 (+ ang (dtr 90)))
                    (setq ghk br-ghk1)
                    (p-data4)
                    (endconn-flg p4 ang)
                    (endconn-val p5 endang)
                )
                ((= (+ ang (dtr 90)) endang)
                    (p-data4)
                    (endconn-val p6 endang)
                    (setq ghk br-ghk1)
                    (endconn-flg p4 ang)
                    (endconn-flg p5 (+ ang (dtr 180)))
                )
            )
        )
        (progn
            (endconn-flg p6 (+ ang (dtr 90)))
            (setq ghk br-ghk1)
            (endconn-flg p4 ang)
            (endconn-flg p5 (+ ang (dtr 180)))
        )
    )
)
;;;;;;section down straight tee lisp ( D-4 )
(defun sstdn(/ p1 p2 ang)
    (pse1)
    (setvar "osmode" 32)
    (setq p1 (getpoint    "\n     Tee center point:[Default = int  point]:"))
    (setvar "osmode" 512)
    (setq p2 (getpoint p1 "\n     Select pipe line:[Default = nea point]:"))
    (SETQ ang (ANGLE P1  P2))
    (sub_tee6)
    (sstdn1 ang p2 p1)
    (pse2)
)
             ;ang   p2    p1
(defun sstdn1(tee-1 tee-2 tee-3 / ang p1 p2 p11 p12 p13 p14 p4 p41 p42 p5
              p51 p52 p1sel cen1 cen2 p2sel p7 p8 p9 p10 p11 p12 p13 p14
              p15 p61 p62 p63 p64)
    (setq tee-type 2)
    (setq ang tee-1)
    (setq p2  tee-2)
    (setq p1  tee-3)
    (p-data1)
    (p-data4)
    (sub_tee3 tee piphd)
    (sub_tee5 p1 (+ ang (dtr 90)) ghk)
    (sub_tee4 piphd flghd ghk)
    (setq tee-type nil)
    (setvar "osmode" 0)
    (if (/= withval nil)
        (progn
            (setq endang (getangle tee-3 "\n     Valve Direction : "))
            (cond
                ((= ang endang)
                    (endconn-val p4 endang)
                    (endconn-flg p5 (+ ang (dtr 180)))
                    (endconn-flg p7 (+ ang (dtr 90)))
                )
                ((= (+ ang (dtr 180)) endang)
                    (endconn-val p5 endang)
                    (endconn-flg p4 ang)
                    (endconn-flg p7 (+ ang (dtr 90)))
                )
                ((= (+ ang (dtr 90)) endang)
                    (endconn-val p7 endang)
                    (endconn-flg p4 ang)
                    (endconn-flg p5 (+ ang (dtr 180)))
                )
            )
        )
        (progn
            (endconn-flg p4 ang)
            (endconn-flg p5 (+ ang (dtr 180)))
            (endconn-flg p7 (+ ang (dtr 90)))
        )
    )
)

;;;;;;section down straight tee lisp ( D-7 )
(defun srtdn(/ p1 p2 ang)
    (pse1)
    (setvar "osmode" 32)
    (setq p1 (getpoint "\n     Tee center point:[Default = int point]:"))(terpri)
    (setvar "osmode" 512)
    (setq p2 (getpoint p1 "\n     Select pipe line:[Default = nea point]:"))(terpri)
    (SETQ ang (ANGLE P1  P2))
    (sub_tee6)
    (srtdn1 ang p2 p1)
    (pse2)
)             ;ang   p2    p1
(defun srtdn1(tee-1 tee-2 tee-3 / cen1 cen2 p11 rt piphd2 br-len br-dia
              br-ghk br-ghk1 p12 p13 p14 p4 p41 p42 p5 p51 p52 p61 p62
              p2sel p7 p8 p9 p10 p11 p12 p13 p14 p15 p63 p64)
    (setq tee-type 5)
    (setq ang tee-1)
    (setq p2  tee-2)
    (setq p1  tee-3)
    (p-data1)
    (redtee)
    (if (= ok 1)
        (progn
            (sub_tee3 tee piphd)
            (setq br-ghk1 ghk)
            (setq ghk br-ghk)
            (p-data1)
            (p-data4)
            (sub_tee5 p1 (+ ang (dtr 90)) ghk)
            (sub_tee4 piphd flghd br-ghk1)
        )
    )
    (setq tee-type nil)
    (if (/= withval nil)
        (progn
            (setq endang (getangle tee-3 "\n     Valve Direction : "))
            (cond
                ((= ang endang)
                    (endconn-flg p7 (+ ang (dtr 90)))
                    (setq ghk br-ghk1)
                    (endconn-flg p5 (+ ang (dtr 180)))
                    (endconn-val p4 endang)
                )
                ((= (+ ang (dtr 180)) endang)
                    (endconn-flg p7 (+ ang (dtr 90)))
                    (setq ghk br-ghk1)
                    (endconn-flg p4 ang)
                    (endconn-val p5 endang)
                )
                ((= (+ ang (dtr 90)) endang)
                    (endconn-val p7 endang)
                    (setq ghk br-ghk1)
                    (endconn-flg p4 ang)
                    (endconn-flg p5 (+ ang (dtr 180)))
                )
            )
        )
        (progn
            (endconn-flg p7 (+ ang (dtr 90)))
            (setq ghk br-ghk1)
            (endconn-flg p4 ang)
            (endconn-flg p5 (+ ang (dtr 180)))
        )
    )
)

;;;;;;section up straight tee lisp ( D-5 )
(defun sstup(/ p1 p2 ang wdown1)
    (pse1)
    (setvar "osmode" 32)
    (setq p1 (getpoint "\n     Tee center point:[Default = int  point]:"))
    (setvar "osmode" 512)
    (setq p2 (getpoint p1 "\n     Select pipe line:[Default = nea point]:"))
    (SETQ ang (ANGLE P1  P2))
    (sub_tee6)
    (sstup1 ang p2 p1)
    (pse2)
)             ;ang   p2    p1
(defun sstup1(tee-1 tee-2 tee-3 / p4 p41 p42 p5 p51 p52 p6 p61 p62 p7 p8
              p9 p10 p11 p12 p13 pt4)
    (setq tee-type 3)
    (setq ang tee-1)
    (setq p2  tee-2)
    (setq p1  tee-3)
    (p-data1)
    (p-data4)
    (setq p1sel(ssget p1))
    (if (/= p1sel nil)
        (if (= wdown "W")
            (command "break" (polar p1 ang flghd) (polar p1 (+ ang (dtr 180)) flghd))
            (command "break" (polar p1 ang piphd) (polar p1 (+ ang (dtr 180)) piphd))
        )
    )
    (sub_tee3 tee piphd)
    (sub_tee7 p1 (+ ang (dtr 90)))
    (setq tee-type nil)
    (if (/= withval nil)
        (progn
            (setq endang (getangle tee-3 "\n     Valve Direction : "))
            (cond
                ((= ang endang)
                    (endconn-flg pt4 (+ ang (dtr 90)))
                    (endconn-flg p5 (+ ang (dtr 180)))
                    (endconn-val p4 endang)
                )
                ((= (+ ang (dtr 180)) endang)
                    (endconn-flg p4 ang)
                    (endconn-flg pt4 (+ ang (dtr 90)))
                    (endconn-val p5 endang)
                )
                ((= (+ ang (dtr 90)) endang)
                    (endconn-flg p4 ang)
                    (endconn-flg p5 (+ ang (dtr 180)))
                    (endconn-val pt4 endang)
                )
            )
        )
        (progn
            (endconn-flg pt4 (+ ang (dtr 90)))
            (endconn-flg p4 ang)
            (endconn-flg p5 (+ ang (dtr 180)))
        )
    )
)

;;;;;;section up straight tee lisp ( D-8 )
(defun srtup(/ p1 p2 ang wdown1)
    (pse1)
    (setvar "osmode" 32)
    (setq p1 (getpoint "\n     Tee center point:[Default = int  point]:"))
    (setvar "osmode" 512)
    (setq p2 (getpoint p1 "\n     Select pipe line:[Default = nea point]:"))
    (SETQ ang (ANGLE P1  P2))
    (sub_tee6)
    (srtup1 ang p2 p1)
    (pse2)
)             ;ang   p2    p1
(defun srtup1(tee-1 tee-2 tee-3 / cen1 cen2 rt piphd2 br-len br-dia
              br-ghk br-ghk1 p4 p41 p42 p5 p51 p52 p6 p61 p62 p7 p8
              p9 p10 p11 p12 p13 pt4)
    (setq tee-type 3)
    (setq ang tee-1)
    (setq p2  tee-2)
    (setq p1  tee-3)
    (p-data1)
    (setq p1sel(ssget p1))
    (redtee)
    (if (= ok 1)
        (progn
            (sub_tee3 tee piphd)
            (setq br-ghk1 ghk)
            (setq ghk br-ghk)
            (p-data1)
            (p-data4)
            (if (/= p1sel nil)
                (if (= wdown "W")
                    (command "break" (polar p1 ang flghd) (polar p1 (+ ang (dtr 180)) flghd))
                    (command "break" (polar p1 ang piphd) (polar p1 (+ ang (dtr 180)) piphd))
                )
            )
            (sub_tee7 p1 (+ ang (dtr 90)))
        )
    )
    (setq tee-type nil)
    (if (/= withval nil)
        (progn
            (setq endang (getangle tee-3 "\n     Valve Direction : "))
            (cond
                ((= ang endang)
                    (endconn-flg pt4 (+ ang (dtr 90)))
                    (setq ghk br-ghk1)
                    (endconn-val p4 endang)
                    (endconn-flg p5 (+ ang (dtr 180)))
                )
                ((= (+ ang (dtr 180)) endang)
                    (endconn-flg pt4 (+ ang (dtr 90)))
                    (setq ghk br-ghk1)
                    (endconn-val p5 endang)
                    (endconn-flg p4 ang)
                )
                ((= (+ ang (dtr 90)) endang)
                    (endconn-val pt4 endang)
                    (setq ghk br-ghk1)
                    (endconn-flg p4 ang)
                    (endconn-flg p5 (+ ang (dtr 180)))
                )
            )
        )
        (progn
            (endconn-flg pt4 (+ ang (dtr 90)))
            (setq ghk br-ghk1)
            (endconn-flg p4 ang)
            (endconn-flg p5 (+ ang (dtr 180)))
        )
    )
)

(defun redtee(/ mainum1 s-num lst1 lst1- lst20- lst30- lst40- lst50-
                br-size)
 (setq dcl_id (load_dialog "C:/GHK/LSP/redtee.dcl"))
 (if (not (new_dialog "redtee" dcl_id))
     (exit)
 )
 (p-data "tee")
 (setq mainum1 "0")
 (if (not pset-s1)(load"c:/ghk/lsp/P_RESET"))
 (pset-s1)
 (setq s-num (- (atoi sizenum) 3))
 (setq lst1- (nth s-num lst1))
 (setq lst20- (nth 0 lst1-));brencht size
 (setq lst30- (nth 1 lst1-));brencht length
 (setq lst40- (nth 2 lst1-));ansi pipe dia
 (setq lst50- (nth 3 lst1-));jis pipe dia
 (setq lst60- (nth 4 lst1-));brencht ghk
 (setq br-size(nth 0 lst20-))
 (setq br-ghk (atoi (nth 0 lst60-)))
 (setq br-len (nth 0 lst30-))
 (if (= 1 ks-)
     (setq br-dia(nth 0 lst50-))
     (setq br-dia(nth 0 lst40-))
 )
 (action_tile "br_size"  "(br_1 (setq mainum1 $value))")
 (action_tile "ansicode" "(setq ansi- 1 ks- 0)(pset-s1)")
 (action_tile "kscode"   "(setq ansi- 0 ks- 1)(pset-s1)")
 (action_tile "zbr-len"  "(setq br-len $value)")
 (action_tile "zbr-dia"  "(setq br-dia $value)")
 (action_tile "zchsize"  "(setq chsize $value)")
 (start_list "br_size")
 (mapcar 'add_list lst20-)
 (end_list)
 (set_tile "br_size" "0")
 (set_tile "zbr-len" br-len)
 (set_tile "zbr-dia" br-dia)
 (set_tile "zchsize" chsize)
 (setq ok(start_dialog))
 (done_dialog)
 (unload_dialog dcl_id)
 (princ)
)

(defun br_1(data)
 (setq lst20- (nth 0 lst1-));brencht length
 (setq lst30- (nth 1 lst1-));brencht length
 (setq lst40- (nth 2 lst1-));ansi pipe dia
 (setq lst50- (nth 3 lst1-));jis pipe dia
 (setq lst60- (nth 4 lst1-));brencht ghk
 (setq br-size(nth (atoi data) lst20-))
 (setq br-ghk (atoi (nth (atoi data) lst60-)))
 (setq br-len (nth (atoi data) lst30-))
 (if (= 1 ks-)
     (setq br-dia(nth (atoi data) lst50-))
     (setq br-dia(nth (atoi data) lst40-))
 )
 (set_tile "zbr-len" br-len)
 (set_tile "zbr-dia" br-dia)
 (set_tile "zchsize" chsize)
)

;;;;;;;;;;;;;;;;tee   piphd
(defun sub_tee1(tee-1 tee-2 / )
    (setq p4 (polar p1 ang tee-1))
    (setq p41 (polar p4 (+ ang (dtr 90)) tee-2))
    (setq p42 (polar p4 (+ ang (dtr 270)) tee-2))
    (setq p5 (polar p1 (+ ang (dtr 180)) tee-1))
    (setq p51 (polar p5 (+ ang (dtr 90)) tee-2))
    (setq p52 (polar p5 (+ ang (dtr 270)) tee-2))
    (setvar "osmode" 0)
    (ls1)
    (cond
        ((or (< ghk sock) (>= ghk double))
            (command "line" p41 p42 "")
            (command "line" p51 p52 "")
        )
        ((< ghk double)
            (weld-mark p4)
            (weld-mark p5)
        )
    )
);;;;;;;;;;;;;;;r-tee piphd2
(defun sub_tee2(tee-1 tee-2 / )
    (setq p6 (polar p1 (+ ang (dtr 90)) tee-1))
    (setq p61 (polar p6 ang tee-2))
    (setq p62 (polar p6 (+ ang (dtr 180)) tee-2))
    (setvar "osmode" 0)
    (ls1)
    (cond
        ((or (< ghk sock) (>= ghk double))
            (command "line" p61 p62 "")
        )
        ((< ghk double)
            (weld-mark p6)
        )
    )
);;;;;;;;;;;;;;;tee   piphd
(defun sub_tee3(tee-1 tee-2  / )
    (setq p4 (polar p1 ang tee-1))
    (setq p41 (polar p4 (+ ang (dtr 90)) tee-2))
    (setq p42 (polar p4 (+ ang (dtr 270)) tee-2))
    (setq p5 (polar p1 (+ ang (dtr 180)) tee-1))
    (setq p51 (polar p5 (+ ang (dtr 90)) tee-2))
    (setq p52 (polar p5 (+ ang (dtr 270)) tee-2))
    (setvar "osmode" 0)
    (ls1)
    (cond
        ((or (< ghk sock) (>= ghk double))
            (command "line" p41 p42 "")
            (command "line" p51 p52 "")
        )
        ((< ghk double)
            (weld-mark p4)
            (weld-mark p5)
        )
    )
);;;;;;;;;;;;;;;piphd flghd
(defun sub_tee4(tee-1 tee-2 tee-3)
    (setq p11 (polar p1 (+ ang (dtr 45)) tee-1))
    (setq p12 (polar p1 (+ ang (dtr 315)) tee-1))
    (setq p13 (polar p1 (+ ang (dtr 135)) tee-1))
    (setq p14 (polar p1 (+ ang (dtr 225)) tee-1))
    (setq p61 (polar p1 (+ ang (dtr 45)) tee-2))
    (setq p62 (polar p1 (+ ang (dtr 315)) tee-2))
    (setq p63 (polar p1 (+ ang (dtr 135)) tee-2))
    (setq p64 (polar p1 (+ ang (dtr 225)) tee-2))
    (if (= wdown "W")
        (progn
            (setq cen1 (polar p1 (+ ang (dtr 90)) (* tee-2 1.3)))
            (setq cen2 (polar p1 (+ ang (dtr 270)) (* tee-2 1.3)))
        )
        (progn
            (setq cen1 (polar p1 (+ ang (dtr 90)) (* tee-1 1.3)))
            (setq cen2 (polar p1 (+ ang (dtr 270)) (* tee-1 1.3)))
        )
    )
    (setvar "osmode" 0)
    (if (or (= tee-type 2) (= tee-type 5))
        (cond
            ((< tee-3 double)
                (if (< tee-3 large)
                    (command "layer" "s" "3C" "")
                    (command "layer" "s" "5C" "")
                )
                (command "arc" "c" p1 p11 p13)
                (command "arc" "c" p1 p14 p12)
                (if (= wdown "W")
                    (progn
                        (command "arc" "c" p1 p61 p63)
                        (command "arc" "c" p1 p64 p62)
                    )
                )
            )
            ((>= tee-3 double)
                (command "layer" "s" "5H" "")
                (command "circle" p1 tee-1)
                (if (= wdown "W")
                    (command "circle" p1 tee-2)
                )
            )
        )
    )
    (command "layer" "s" "1c" "")
    (command "line" cen1 cen2 "")
);;;;;;;;;;;;;;;p1     ang    ghk ,br-ghk
(defun sub_tee5(elbow1 elbow2 elbow3)
    (setvar "osmode" 0)
    (if (= radu- "S")(setq elbow90 elbow90s)(setq elbow90 elbow90l))
    (setq p2sel nil)
    (setq p7 (polar elbow1 elbow2 elbow90))
    (setq p2sel(ssget p7))
    (setq p8 (polar p7 (+ elbow2 (dtr 90)) piphd))
    (setq p9 (polar p7 (+ elbow2 (dtr 270)) piphd))
    (setq p10 (polar elbow1 (+ elbow2 (dtr 90)) piphd))
    (setq p11 (polar elbow1 (+ elbow2 (dtr 270)) piphd))
    (if (= wdown "W")
       (setq p12 (polar elbow1 elbow2 flghd))
       (setq p12 (polar elbow1 elbow2 piphd))
    )
    (setq p13 (polar elbow1 elbow2 (sqrt (- (* flghd flghd) (* piphd piphd)))))
    (setq p14 (polar p13 (+ elbow2 (dtr 90)) piphd))
    (setq p15 (polar p13 (+ elbow2 (dtr 270)) piphd))
    (if (< elbow3 sock)
        (progn
            (command "layer" "s" "5C" "")
            (command "line" p8 p9 "")
            (if (= p2sel nil)
                (command "line" p12 p7 "")
                (entt-ch1 p2sel elbow1 p12)
            )
        )
        (if (< elbow3 double)
            (progn
                (if (< elbow3 large)
                    (command "layer" "s" "5C" "")
                    (command "layer" "s" "8C" "")
                )
                (if (= p2sel nil)
                    (command "line" p12 p7 "")
                    (entt-ch1 p2sel elbow1 p12)
                )
                (weld-mark p7)
            )
            (progn
                (command "line" p14 p8 p9 p15 "")
            )
        )
    )
)

(defun sub_tee6(/ wdown1)
    (if (= wdown nil)(setq wdown "N"))
    (terpri)
    (prompt               "     With Down Flange [ With flg / with Not flg")
    (if (= wdown "W")
        (prompt "< With > ]")
        (prompt "< Not > ]")
    )
    (initget "W N")
    (setq wdown1(getkword ""))
    (terpri)
    (if (= wdown1 nil)(setq wdown wdown)(setq wdown wdown1))
);;;;;;;;;;;;;;;p1     ang
(defun sub_tee7(elbow1 elbow2 / pt2sel elbow pt5 pt6 pt8 pt7 pt9 pt10 pt11
                pt12 pt13 pt14 pt15 pt16 pt17 pt11a)
    (setvar "osmode" 0)
    (p-data1)
    (p-data4)
    (setq pt2sel nil)
    (if (= radu- "S")(setq elbow90 elbow90s)(setq elbow90 elbow90l))
    (setq pt4 (polar elbow1 elbow2 elbow90))
    (setq pt5 (polar elbow1 (+ elbow2 (dtr 45)) piphd))
    (setq pt6 (polar elbow1 (+ elbow2 (dtr 315)) piphd))
    (setq pt7 (polar elbow1 (+ elbow2 (dtr 45)) flghd))
    (setq pt8 (polar elbow1 (+ elbow2 (dtr 315)) flghd))
    (setq pt9 (polar elbow1 (+ elbow2 (dtr 90)) piphd))
    (setq pt10 (polar elbow1 (+ elbow2 (dtr 270)) piphd))
    (setq pt11a(polar elbow1 elbow2 (sqrt (- (* flghd flghd) (* piphd piphd)))))
    (setq pt11 (polar pt11a (+ elbow2 (dtr 90)) piphd))
    (setq pt12 (polar pt11a (+ elbow2 (dtr 270)) piphd))
    (setq pt13 (polar pt4 (+ elbow2 (dtr 90)) piphd))
    (setq pt14 (polar pt4 (+ elbow2 (dtr 270)) piphd))
    (if (= wdown "W")
        (progn
            (setq pt15 (polar elbow1 (+ elbow2 (dtr 180)) (* flghd 1.3)))
            (setq pt16 (polar elbow1 (+ elbow2 (dtr 270)) (* flghd 1.3)))
            (setq pt17 (polar elbow1 (+ elbow2 (dtr 90)) (* flghd 1.3)))
        )
        (progn
            (setq pt15 (polar elbow1 (+ elbow2 (dtr 180)) (* piphd 1.3)))
            (setq pt16 (polar elbow1 (+ elbow2 (dtr 270)) (* piphd 1.3)))
            (setq pt17 (polar elbow1 (+ elbow2 (dtr 90)) (* piphd 1.3)))
        )
    )
    (setq pt2sel(ssget pt4))
    (ls1)
    (cond
        ((< ghk sock)
            (if (= pt2sel nil)
                (command "line" elbow1 pt4 "")
                (entt-ch1 pt2sel elbow1 elbow1)
            )
            (command "line" pt13 pt14 "")
            (command "layer" "s" "3C" "")
            (command "arc" "c" elbow1 pt5 pt6)
            (if (= wdown "W")
                (command "arc" "c" elbow1 pt7 pt8)
            )
        )
        ((< ghk double)
            (if (= pt2sel nil)
                (command "line" elbow1 pt4 "")
                (entt-ch1 pt2sel elbow1 elbow1)
            )
            (weld-mark pt4)
            (if (< ghk large)
                (command "layer" "s" "3C" "")
                (command "layer" "s" "5C" "")
            )
            (command "arc" "c" elbow1 pt5 pt6)
            (if (= wdown "W")
                (command "arc" "c" elbow1 pt7 pt8)
            )
        )
        ((>= ghk double)
            (command "layer" "s" "5C" "")
            (command "arc" "c" elbow1 pt9 pt10)
            (if (= wdown "W")
                (command "arc" "c" elbow1 pt11 pt12)
            )
            (command "line" pt9 pt13 pt14 pt10 "")
        )
    )
    (command "layer" "s" "1E" "")
    (command "line" elbow1 pt15 "")
    (command "line" pt16 pt17 "")
)
