;<<<<<<<<<<<<<<<<<<<<<<<< AUTO CAD LISP >>>>>>>>>>>>>>>>>>>>>>>>>>>>>>>
;~~~~~~~~~~~~~~~~~~~~~~~~GATE VALVE SIDE LISP~~~~~~~~~~~~~~~~~~~~~~~~~~
(defun diavf(/ a-pip k-pip flglen flgd flgthk hubdia flghd stubl p2sel
               stubl1 stubd vall vall1 vall2 len p1 p2 ang vall-1)
    (if (/= job_direc 1)
        (pse1)
    )
    (p-data3)
    (p-data4)
    (p-data5 "diav")
    (if (= dia-type nil)(setq dia-type 1))
    (if (> vall 1)
        (progn
            (endflgtype)
            (if (= job_direc 1)
                (progn
                    (setq p2 endpoint)
                    (setq ang endang)
                    (setq p2sel(ssget p2))
                )
                (progn
                    (setvar "osmode" 512)
                    (setq p1 (getpoint    "\nSelection point :[Default = nea point]:"))
                    (setvar "osmode" 512)
                    (setq p2 (getpoint p1 "\nSecond point    :[Default = nea point]:"))
                    (setq p2sel(ssget p2))
                    (setvar "osmode" 0)
                    (setq ang (angle p1 p2))
                )
            )
            (terpri)
            (prompt "Do you want flange to flange dimension < Default =")
            (princ vall)
            (prompt " > : ")
            (setq vall-1(getreal ""))
            (terpri)
            (if (= vall-1 nil)(setq vall vall)(setq vall vall-1))
            (if (or (= flg_end "F")(= flg_end "W")(= flg_end nil))
                (setq len (+ vall ga))
                (setq len vall)
            )
            (if (/= p2sel nil)
                (command "break" p2 (polar p2 ang len))
            )
            (command "layer" "s" "1E" "")
            (command "line" p2 (polar p2 ang len) "")
            (if (or (= flg_end "F") (= flg_end "W"))
                (progn
                    (if (not val-flg)(load"c:/ghk/lsp/val-flg"))
                    (val-flg ang p2)
                    (val-flg (+ ang (dtr 180)) (polar p2 ang len))
                )
            )
            (diabase ang p2 p1)
        )
        (prompt "\n    IS NOT SIZE")
    )
    (if (/= job_direc 1)
        (pse2)
    )
)

(defun diabase(dia-par1 dia-par2 dia-par3 / val_1 val_2 val1 val2 val3
                  val4 h1 h2)
    (if (not valve)(load"c:/ghk/lsp/valve"))
    (valve dia-par1 dia-par2)
    (setq h1 (polar dia-par2 dia-par1 (/ len 2)))
    (setq h2 (polar h1 (+ dia-par1 (dtr 90)) (* 1.4 flghd)))
    (command "layer" "s" "2C" "")
    (if (= 1 dia-type)
        (progn
            (command "pline" val1 "w" "0" "0" val3 val2 val4 val1 "")
            (command "arc" val1 h2 val2)
        )
        (command "pline" val1 "w" "0" "0" val2 val3
        (polar (polar val3 (+ dia-par1 (dtr 90)) (* flghd 1.5)) (+ dia-par1
        (dtr 180)) (/ (distance val1 val2) 2.00))
        val4 val1 "")
    )
)
