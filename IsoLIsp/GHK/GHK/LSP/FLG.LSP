;;;;;;flange 90elbow down lisp ( D-2 )
(defun feldn(/ p1 p2 p3 ang ang1)
    (pse1)
    (setvar "osmode" 33)
    (setq p1 (getpoint    "\n     Elbow end point < end point >:"))
    (setvar "osmode" 0)
    (setq p2 (getpoint p1 "\n     Select pipe line < nea point >:"))
    (setq p3 (getpoint p1 "\n     Select pipe line < nea point >:"))
    (SETQ ang (ANGLE P1  P2))
    (SETQ ang1 (angle P1 P3))
    (feldn1 p1 ang ang1)
    (pse2)
);;;;;;;;;;;;;p1     ang    ang1
(defun feldn1(elbow1 elbow2 elbow3 / p2sel p3sel elbow p4 p5 p6 p7 p8 p9 p10 p11 p12 p13 p14
               p15 p16 p17 p18 p19 p20 p11a p21 p22 p23)
    (setvar "osmode" 0)
    (p-data1)
    (p-data4)
    (setq p2sel nil)
    (setq p3sel nil)
    (if (= radu- "S")(setq elbow90 elbow90s)(setq elbow90 elbow90l))
    (setq p4 (polar elbow1 elbow2 elbow90))
    (setq p5 (polar elbow1 (+ elbow2 (dtr 45)) piphd))
    (setq p6 (polar elbow1 (+ elbow2 (dtr 315)) piphd))
    (setq p7 (polar elbow1 (+ elbow2 (dtr 45)) flghd))
    (setq p8 (polar elbow1 (+ elbow2 (dtr 315)) flghd))
    (setq p9 (polar elbow1 (+ elbow2 (dtr 90)) piphd))
    (setq p10 (polar elbow1 (+ elbow2 (dtr 270)) piphd))
    (setq p11a(polar elbow1 elbow2 (sqrt (- (* flghd flghd) (* piphd piphd)))))
    (setq p11 (polar p11a (+ elbow2 (dtr 90)) piphd))
    (setq p12 (polar p11a (+ elbow2 (dtr 270)) piphd))
    (setq p13 (polar p4 (+ elbow2 (dtr 90)) piphd))
    (setq p14 (polar p4 (+ elbow2 (dtr 270)) piphd))
    (setq p15 (polar elbow1 (+ elbow2 (dtr 180)) (* flghd 1.3)))
    (setq p16 (polar elbow1 (+ elbow2 (dtr 270)) (* flghd 1.3)))
    (setq p17 (polar elbow1 (+ elbow2 (dtr 90)) (* flghd 1.3)))
    (setq p18 (polar elbow1 elbow3 elbow90))
    (setq p2sel(ssget p4))
    (setq p3sel(ssget p18))
    (setq p19 (polar p18 (+ elbow3 (dtr 90)) piphd))
    (setq p20 (polar p18 (+ elbow3 (dtr 270)) piphd))
    (setq p21 (polar elbow1 elbow3 (sqrt (- (* flghd flghd) (* piphd piphd)))))
    (setq p22 (polar p21 (+ elbow3 (dtr 90)) piphd))
    (setq p23 (polar p21 (+ elbow3 (dtr 270)) piphd))
    (ls1)
    (cond
        ((< ghk sock)
            (if (/= elbow2 elbow3)
                (progn
                    (command "line" p19 p20 "")
                    (if (= p3sel nil)
                        (command "line" (polar elbow1 elbow3 flghd) p18 "")
                        (entt-ch1 p3sel elbow1 (polar elbow1 elbow3 flghd))
                    )
                )
            )
            (if (= p2sel nil)
                (command "line" elbow1 p4 "")
                (entt-ch1 p2sel elbow1 elbow1)
            )
            (command "line" p13 p14 "")
            (command "layer" "s" "3C" "")
            (command "arc" "c" elbow1 p5 p6)
            (command "arc" "c" elbow1 p7 p8)
        )
        ((< ghk double)
            (if (= p2sel nil)
                (command "line" elbow1 p4 "")
                (entt-ch1 p2sel elbow1 elbow1)
            )
            (if (/= elbow2 elbow3)
                (progn
                    (weld-mark p18)
                    (if (< ghk large)
                        (command "layer" "s" "5C" "")
                        (command "layer" "s" "8C" "")
                    )
                    (if (= p3sel nil)
                        (command "line" (polar elbow1 elbow3 flghd) p18 "")
                        (entt-ch1 p3sel elbow1 (polar elbow1 elbow3 flghd))
                    )
                )
            )
            (weld-mark p4)
            (if (< ghk large)
                (command "layer" "s" "3C" "")
                (command "layer" "s" "5C" "")
            )
            (command "arc" "c" elbow1 p5 p6)
            (command "arc" "c" elbow1 p7 p8)
        )
        ((>= ghk double)
            (command "layer" "s" "5C" "")
            (command "arc" "c" elbow1 p9 p10)
            (command "arc" "c" elbow1 p11 p12)
            (command "line" p9 p13 p14 p10 "")
            (if (/= elbow2 elbow3)
                (command "line" p22 p19 p20 p23 "")
            )
        )
    )
    (command "layer" "s" "1E" "")
    (command "line" elbow1 p15 "")
    (command "line" p16 p17 "")
    (if (/= withval nil)
        (if (/= elbow2 elbow3)
            (progn
                (setq endang (getangle elbow1 "\n     Valve Direction : "))
                (cond
                    ((= elbow2 endang)
                        (endconn-val p4 endang)
                        (endconn-flg p18 elbow3)
                    )
                    ((= elbow3 endang)
                        (endconn-val p18 endang)
                        (endconn-flg p4 elbow2)
                    )
                )
            )
            (endconn-val p4 elbow2)
        )
        (progn
            (endconn-flg p4 elbow2)
            (if (/= elbow2 elbow3)
                (endconn-flg p18 elbow3)
            )
        )
    )
)
;;;;;;equipment flange nozzle lisp ( B-1 )
(defun flg(/ p1 p2 ang p3 p4 p5 p6 p7 p8 p9 p10 p11)
    (pse1)
    (setvar "osmode" 32)
    (setq p1 (getpoint    "\n     Selection point:[Default = int point]:"))
    (setvar "osmode" 512)
    (setq p2 (getpoint p1 "\n     Second point:[Default = nea point]:"))
    (setvar "osmode" 0)
    (setq ang (angle P1  P2))
    (p-data1)
    (p-data4)
    (setq p3 (polar p1 ang 150))
    (setq p4 (polar p3 (+ ang (dtr 90)) flghd))
    (setq p5 (polar p4 (+ ang (dtr 270)) flgd))
    (setq p6 (polar p4 (+ ang (dtr 180)) flgthk))
    (setq p7 (polar p6 (+ ang (dtr 270)) (- flghd piphd)))
    (setq p8 (polar p6 (+ ang (dtr 270)) (+ flghd piphd)))
    (setq p9 (polar p6 (+ ang (dtr 270)) flgd))
    (setq p10 (polar p7 (+ ang (dtr 180)) (- 150 flgthk)))
    (setq p11 (polar p8 (+ ang (dtr 180)) (- 150 flgthk)))
    (command "layer" "s" "2C" "")
    (command "pline" p6 "w" "0" "0" p4 p5 p9 p6 "")
    (command "line" p7 p10 "")
    (command "line" p8 p11 "")
    (if (not val-flg)(load"c:/ghk/lsp/val-flg"))
    (val-flg (+ ang (dtr 180)) (polar p3 ang g))
    (pse2)
)
;;;;;;Front flange section lisp ( A-4 )
(defun flgt(/ p1 p2 ang)
    (pse1)
    (setvar "osmode" 1)
    (setq p1 (getpoint    "\n     Section point: [Default = end point]:"))
    (setvar "osmode" 512)
    (setq p2 (getpoint p1 "\n     Select pipe line: [Default = nea point]:"))
    (SETQ ang (ANGLE P1 P2))
    (flgt1 p1 ang)
    (pse2)
);;;;;;;;;;;;p1     ang
(defun flgt1(elbow1 elbow2 / p2sel p3 p4 p5 p6 p7 p8 p9 p10 p11 p12 p13
             p14 p15 insul)
    (setvar "osmode" 0)
    (p-data1)
    (p-data4)
    (setq p2sel nil)
    (if (= withins "ON")
        (progn
            (if (not in-thk)(setq in-thk 50))
            (prompt "\n     Do you want insulation thickness < ")
            (princ in-thk)
            (prompt " t> : ")
            (setq insul(getint ""))
            (if (= insul nil)(setq insul in-thk)(setq in-thk insul))
            (setq insul(+ flghd insul))
        )
    )
    (if (= radu- "S")(setq elbow90 elbow90s)(setq elbow90 elbow90l))
    (if (= withins "ON")
        (progn
            (setq p3 (polar elbow1 (+ elbow2 3.14159) (* 1.1 insul)))
            (setq p5 (polar elbow1 (+ elbow2 1.5708) (* 1.1 insul)))
            (setq p6 (polar elbow1 (- elbow2 1.5708) (* 1.1 insul)))
        )
        (progn
            (setq p3 (polar elbow1 (+ elbow2 3.14159) (* 1.3 flghd)))
            (setq p5 (polar elbow1 (+ elbow2 1.5708) (* 1.3 flghd)))
            (setq p6 (polar elbow1 (- elbow2 1.5708) (* 1.3 flghd)))
        )
    )
    (setq p4 (polar elbow1 elbow2 flghd))
    (setq p7 (polar elbow1 elbow2 elbow90))
    (setq p2sel(ssget p7))
    (setq p8 (polar p7 (+ elbow2 (dtr 90)) piphd))
    (setq p9 (polar p7 (+ elbow2 (dtr 270)) piphd))
    (setq p10 (polar elbow1 (+ elbow2 (dtr 90)) piphd))
    (setq p11 (polar elbow1 (+ elbow2 (dtr 270)) piphd))
    (setq p12 (polar elbow1 elbow2 flghd))
    (setq p13 (polar elbow1 elbow2 (sqrt (- (* flghd flghd) (* piphd piphd)))))
    (setq p14 (polar p13 (+ elbow2 (dtr 90)) piphd))
    (setq p15 (polar p13 (+ elbow2 (dtr 270)) piphd))
    (if (= withins "ON")
        (progn
            (c:lst1)
            (command "circle" p1 insul)
            (command "circle" p1 flghd)
            (command "layer" "s" "1C" "")
            (command "hatch" "dots,o" (* s (if (< ghk large) 7 (if (< ghk double) 10 20))) "0" (ss-add) "")
            (command "erase" "p" "")
            (command "layer" "s" "2C" "")
            (command "circle" p1 insul)
        )
    )
    (if (< ghk large)
        (command "layer" "s" "3C" "")
        (command "layer" "s" "5C" "")
    )
    (command "circle" elbow1 flghd)
    (c:lst1)
    (command "circle" elbow1 piphd)
    (command "layer" "s" "1C" "")
    (if (< ghk large)
        (command "hatch" "ansi31" (* s 7) "0" (ss-add) "")
        (progn
            (c:lst1)
            (command "layer" "s" "2C" "")
            (command "pline" p10 "a" "r" (/ piphd 2.00) p1 p11 "s" (polar elbow1 elbow2 piphd) p10 "")
            (command "layer" "s" "1C" "")
            (command "hatch" "ansi31" (* s 10) "0" (ss-add) "")
        )
    )
    (if (< ghk sock)
        (progn
            (command "layer" "s" "5C" "")
            (command "line" p8 p9 "")
            (if (= p2sel nil)
                (command "line" (polar elbow1 elbow2 flghd) p7 "")
                (entt-ch1 p2sel elbow1 p12)
            )
        )
        (if (< ghk double)
            (progn
                (if (< ghk large)
                    (command "layer" "s" "5C" "")
                    (command "layer" "s" "8C" "")
                )
                (if (= p2sel nil)
                    (command "line" (polar elbow1 elbow2 flghd) p7 "")
                    (entt-ch1 p2sel elbow1 p12)
                )
                (weld-mark p7)
            )
            (progn
                (command "line" p14 p8 p9 p15 "")
            )
        )
    )
    (command "layer" "s" "1E" "")
    (command "line" p3 p4 "")
    (command "line" p5 p6 "")
    (if (/= withval nil)
        (endconn-val p7 elbow2)
        (endconn-flg p7 elbow2)
    )
)
;;;;;;flange nozzle lisp ( B-2 )
(defun sofflg(/ p1 p2 ang p11 p12 p3 p31 p32 p33 p34 p4 p41 p42)
    (pse1)
    (setvar "osmode" 512)
    (setq p1 (getpoint    "\n     Selection point:[Default = nea point]:"))
    (setvar "osmode" 544)
    (setq p2 (getpoint p1 "\n     Second point:[Default = int or nea point]:"))
    (SETQ ang (ANGLE P1  P2))
    (p-data4)
    (setq p4  (polar p1 (+ ang (dtr 180)) flglen))
    (setq p11 (polar p4 (+ ang (dtr 90)) (/ hubdia 2)))
    (setq p12 (polar p4 (+ ang (dtr 270)) (/ hubdia 2)))
    (setq p3  (polar p1 (+ ang (dtr 180)) flgthk))
    (setq p31 (polar p3 (+ ang (dtr 90)) flghd))
    (setq p32 (polar p3 (+ ang (dtr 270)) flghd))
    (setq p33 (polar p3 (+ ang (dtr 90)) (/ hubdia 2)))
    (setq p34 (polar p3 (+ ang (dtr 270)) (/ hubdia 2)))
    (setq p41 (polar p1 (+ ang (dtr 90)) flghd))
    (setq p42 (polar p1 (+ ang (dtr 270)) flghd))
    (ls1)
    (if (= flg-type 0)
        (command "pline" p34 "w" "0" "0" p31 p41 p42 p32 p34 p12 p11 p33 "")
        (if (< ghk double)
            (command "line" p41 p42 "")
            (command "pline" p34 "w" "0" "0" p31 p41 p42 p32 p34 p12 p11 p33 "")
        )
    )
    (pse2)
)
;;;;;;flange nozzle lisp ( B-3 )
(defun wnfflg(/ p1 p2 ang p11 p111 p12 p121 p3 p31 p32 p311 p321 p4 p41 p42)
    (pse1)
    (setvar "osmode" 512)
    (setq p1 (getpoint    "\n     Selection point:[Default = nea point]:"))
    (setvar "osmode" 0)
    (setq p2 (getpoint p1 "\n     Second point:[Default = none point]:"))
    (SETQ ang (ANGLE P1  P2))
    (p-data1)
    (p-data4)
    (setq p11  (polar p1 (+ ang (dtr 90)) flghd))
    (setq p111 (polar p1 (+ ang (dtr 90)) (/ hubdia 2)))
    (setq p12  (polar p1 (+ ang (dtr 270)) flghd))
    (setq p121 (polar p1 (+ ang (dtr 270)) (/ hubdia 2)))
    (setq p3   (polar p1 (+ ang (dtr 180)) flgthk))
    (setq p31  (polar p3 (+ ang (dtr 90)) (/ hubdia 2)))
    (setq p32  (polar p3 (+ ang (dtr 270)) (/ hubdia 2)))
    (setq p311 (polar p3 (+ ang (dtr 90)) flghd))
    (setq p321 (polar p3 (+ ang (dtr 270)) flghd))
    (setq p4   (polar p1 (+ ang (dtr 180)) flglen))
    (setq p41  (polar p4 (+ ang (dtr 90)) piphd))
    (setq p42  (polar p4 (+ ang (dtr 270)) piphd))
    (ls1)
    (if (= flg-type 0)
        (command "pline" p31 "w" "0" "0" p32 p42 p41 p31 p311 p11 p12 p321 P32 "")
        (if (< ghk double)
            (progn
                (command "line" p11 p12 "")
                (command "layer" "s" "2C" "")
                (command "solid" p111 p4 p121 p4 ^c)
                (weld-mark p4)
            )
            (command "pline" p31 "w" "0" "0" p32 p42 p41 p31 p311 p11 p12 p321 P32 "")
        )
    )
    (pse2)
)
