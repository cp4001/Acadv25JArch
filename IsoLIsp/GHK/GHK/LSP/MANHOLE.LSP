;;;;;;equipment manhole flange nozzle lisp
(defun manhole(/ a-pip k-pip flglen flgd flgthk hubdia flghd stubl p2sel
               stubl1 stubd vall vall1 vall2 len p1 p2 ang p3 p4 p5 p6
               p7 p8 p9 p10 p11 p12p 13 p14 p15 p16 p17 p18)
    (pse1)
    (setvar "osmode" 32)
    (setq p1 (getpoint "Selection point:[Default = int point]:"))(terpri)
    (setvar "osmode" 512)
    (setq p2 (getpoint p1 "Second point:[Default = nea point]:"))(terpri)
    (setvar "osmode" 0)
    (SETQ ang (ANGLE P1  P2))
    (p-data3)
    (p-data4)
    (setq p3 (polar p1 ang 150))
    (setq p4 (polar p3 (+ ang (dtr 90)) flghd))
    (setq p5 (polar p4 (+ ang (dtr 270)) flgd))
    (setq p6 (polar p4 (+ ang (dtr 180)) flgthk))
    (setq p7 (polar p6 (+ ang (dtr 270)) (- flghd piphd)))
    (setq p8 (polar p6 (+ ang (dtr 270)) (+ flghd piphd)))
    (setq p9 (polar p6 (+ ang (dtr 270)) flgd))
    (setq p10 (polar p7 (+ ang (dtr 180)) (- 150 flgthk)))
    (setq p11 (polar p8 (+ ang (dtr 180)) (- 150 flgthk)))
    (setq p12 (polar p4 ang flgthk))
    (setq p13 (polar p5 ang flgthk))
    (setq p14 (polar p5 (+ ang (dtr 270)) flgthk))
    (setq p15 (polar p14 ang (* flgthk 2)))
    (setq p16 (polar p14 (+ ang (dtr 180)) (* flgthk 2)))
    (setq p17 (polar p14 (+ ang (dtr 270)) (* flgthk 2)))
    (setq p18 (polar p14 (+ ang (dtr 345)) flgd))
    (command "layer" "s" "2C" "")
    (command "pline" p4 "w" "0" "0" p12 p13 p5 p4 p6 p9 p5 "")
    (command "line" p7 p10 "")
    (command "line" p8 p11 "")
    (command "circle" p14 (* S 0.7))
    (command "layer" "s" "2p" "")
    (command "line" p14 p18 "")
    (command "arc" p18 "_e" p12 "_r" flgd)
    (command "layer" "s" "1e" "")
    (command "line" p15 p16 "")
    (command "line" p5 p17 "")
    (pse2)
)
