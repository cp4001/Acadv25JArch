;;;;;;Front angle flange lisp
(defun flg-ang(/ p1 p2 ang ang1 in-ang in-ang1 con p13 p11 p111 p12 p121
                 p3 p33 p31 p311 p32 p321 p4 p5 p51 p52 p6 p61 p62)
    (pse1)
    (setvar "osmode" 32)
    (setq p1 (getpoint "Elbow end point:[Default = int point]:"))(terpri)
    (setvar "osmode" 512)
    (setq p2 (getpoint p1 "First pipe line:[Default = nea point]:"))(terpri)
    (setvar "osmode" 0)
    (SETQ ang (ANGLE P1 P2))
    (SETQ ang1 (ANGLE P2 P1))
    (SETQ in-ang (rtd ang))
    (SETQ in-ang1 (rtd ang1))
    (setq con 0.866025403)
    (setq p13 (polar p1 ang (* 1.5 piphd)))
    (setq p11 (polar p1 (+ ang (dtr 90)) piphd))
    (setq p111 (polar p1 (+ ang (dtr 90)) (* piphd 1.3)))
    (setq p12 (polar p1 (+ ang (dtr 270)) piphd))
    (setq p121 (polar p1 (+ ang (dtr 270)) (* piphd 1.3)))
    (setq p3 (polar p1 (+ ang (dtr 180)) (* 2 piphd)))
    (setq p33 (polar p1 (+ ang (dtr 180)) (* 3.3 piphd)))
    (setq p31 (polar p3 (+ ang (dtr 90)) flghd))
    (setq p311 (polar p3 (+ ang (dtr 90)) (* flghd 1.3)))
    (setq p32 (polar p3 (+ ang (dtr 270)) flghd))
    (setq p321 (polar p3 (+ ang (dtr 270)) (* flghd 1.3)))
    (setq p4 (polar p3 ang (* con softhk)))
    (setq p5 (polar p4 ang (* con softhk)))
    (setq p51 (polar p5 (+ ang (dtr 90)) flghd))
    (setq p52 (polar p5 (+ ang (dtr 270)) flghd))
    (setq p6 (polar p5 ang (* con flghd)))
    (setq p61 (polar p6 (+ ang (dtr 90)) piphd))
    (setq p62 (polar p6 (+ ang (dtr 270)) piphd))
    (c:lst1)
    (command "layer" "s" "2C" "")
    (if (= f-ang 10)(flg-ang1 "*c:/ghk/dwg/10dnd" "*c:/ghk/dwg/flg10"))
    (if (= f-ang 15)(flg-ang1 "*c:/ghk/dwg/15dnd" "*c:/ghk/dwg/flg15"))
    (if (= f-ang 20)(flg-ang1 "*c:/ghk/dwg/20dnd" "*c:/ghk/dwg/flg20"))
    (if (= f-ang 30)(flg-ang1 "*c:/ghk/dwg/30dnd" "*c:/ghk/dwg/flg30"))
    (if (= f-ang 40)(flg-ang1 "*c:/ghk/dwg/40dnd" "*c:/ghk/dwg/flg40"))
    (if (= f-ang 45)(flg-ang1 "*c:/ghk/dwg/45dnd" "*c:/ghk/dwg/flg45"))
    (if (= f-ang 50)(flg-ang1 "*c:/ghk/dwg/50dnd" "*c:/ghk/dwg/flg50"))
    (if (= f-ang 60)(flg-ang1 "*c:/ghk/dwg/60dnd" "*c:/ghk/dwg/flg60"))
    (if (= f-ang 70)(flg-ang1 "*c:/ghk/dwg/70dnd" "*c:/ghk/dwg/flg70"))
    (if (= f-ang 80)(flg-ang1 "*c:/ghk/dwg/80dnd" "*c:/ghk/dwg/flg80"))
    (command "change" (ss-add) "" "p" "la" "2C" "")
    (command "line" p31 p51 "")
    (command "line" p32 p52 "")
    (command "line" p11 p61 "")
    (command "line" p12 p62 "")
    (command "layer" "s" "1e" "")
    (command "line" p111 p121 "")
    (command "line" p311 p321 "")
    (command "line" p311 p321 "")
    (command "extend" p6 "" p61 p62 "")
    (command "line" p13 p33 "")
    (pse2)
)

(defun flg-ang1(flg1 flg2)
    (command "insert" flg1 p1 piphd in-ang1)
    (command "insert" flg2 p3 flghd in-ang)
    (command "insert" flg1 p4 flghd in-ang1)
    (command "insert" flg1 p5 flghd in-ang1)
)
