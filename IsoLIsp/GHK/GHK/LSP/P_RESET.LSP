(defun c:p_reset()
 (setq dcl_id (load_dialog "c:/ghk/lsp/p_reset.dcl"))
  (if (not (new_dialog "p_reset" dcl_id))
      (exit)
  )
 (setq n_weld1  (rtos weld1 2 1))
 (setq n_weld2  (rtos weld2 2 1))
 (setq n_weld3  (rtos weld3 2 1))
 (setq n_sock   (rtos sock 2 0))
 (setq n_large  (rtos large 2 0))
 (setq n_double (rtos double 2 0))
 (setq n_ga     (rtos (/ ga 2.0) 2 1))
 (setq n_weldc  (rtos weldc 2 1))
 (setq o_weld1  weld1)
 (setq o_weld2  weld2)
 (setq o_weld3  weld3)
 (pset-s1)
 (pset-s2)
 (action_tile "ansicode" "(setq ansi- 1 ks- 0)(pset-s1)")
 (action_tile "kscode"   "(setq ansi- 0 ks- 1)(pset-s1)")
 (action_tile "s-flg"    "(setq flg-type 1)(pset-s2)")
 (action_tile "d-flg"    "(setq flg-type 0)(pset-s2)")
 (action_tile "zgasket"  "(setq ga     (atof $value))")
 (action_tile "zweldc"   "(setq weldc  (atof $value))")
 (action_tile "zweld1"   "(setq weld1  (atof $value))")
 (action_tile "zweld2"   "(setq weld2  (atof $value))")
 (action_tile "zweld3"   "(setq weld3  (atof $value))")
 (action_tile "zsock"    "(setq sock   (atof $value))")
 (action_tile "zlarge"   "(setq large  (atof $value))")
 (action_tile "zdouble"  "(setq double (atof $value))")
 (action_tile "defu"     "(defau)")
 (set_tile "zweld1"  n_weld1)
 (set_tile "zweld2"  n_weld2)
 (set_tile "zweld3"  n_weld3)
 (set_tile "zweldc" n_weldc)
 (set_tile "zgasket" n_ga)
 (set_tile "zsock"   n_sock)
 (set_tile "zlarge"  n_large)
 (set_tile "zdouble" n_double)
 (setq ok(start_dialog))
 (done_dialog)
 (unload_dialog dcl_id)
 (if (= ok 1)(we1))
 (princ)
)

(defun we1()
    (setvar "cmdecho" 0)
    (if (/= weld1 o_weld1)(weldchg "P-WELD1" weld1))
    (if (/= weld2 o_weld2)(weldchg "P-WELD2" weld2))
    (if (/= weld3 o_weld3)(weldchg "P-WELD3" weld3))
    (weldchg "FLOWMARK" s)
    (setq ga (* ga 2))
)

(defun weldchg(n-weld1 n-weld2 / i ia sss l en el d1 b1 w-size1 w-size3 b2 d2)
    (setq i 0)
    (setq ia 0)
    (setq sss(ssget "X" (list (cons 2 n-weld1))))
    (if (/= sss nil)
        (progn
            (setq l(sslength sss))
            (repeat l
                (setq en(ssname sss i))
                (setq el (entget en))
                (setq w-size1 (assoc 41 el))
                (setq d1 (cons (car w-size1) n-weld2))
                (setq b1 (subst d1 w-size1 el))
                (entmod b1)
                (setq i(+ 1 i))
            )
            (repeat l
                (setq en(ssname sss ia))
                (setq el (entget en))
                (setq w-size3 (assoc 42 el))
                (setq d2 (cons (car w-size3) n-weld2))
                (setq b2 (subst d2 w-size3 el))
                (entmod b2)
                (setq ia(+ 1 ia))
            )
        )
    )
)

(defun defau()
    (setq WELD1 (* S 0.9))
    (setq WELD2 (* S 1.3))
    (setq WELD3 (* S 0.5))
    (setq sock  50)
    (setq large 80)
    (setq double 300)
    (setq ga 3)
    (setq weldc 3)
    (set_tile "zweldc" "3")
    (set_tile "zgasket" "3")
    (set_tile "zweld1"  (rtos weld1 2 1))
    (set_tile "zweld2"  (rtos weld2 2 1))
    (set_tile "zweld3"  (rtos weld3 2 1))
    (set_tile "zsock"   "50")
    (set_tile "zlarge"  "80")
    (set_tile "zdouble" "300")
)
(defun pset-s1()
 (if (= 1 ks-)
      (set_tile "kscode" "1")
      (set_tile "ansicode" "1")
 )
)

(defun pset-s2()
 (if (= flg-type 0)
      (set_tile "d-flg" "1")
      (set_tile "s-flg" "1")
 )
)
