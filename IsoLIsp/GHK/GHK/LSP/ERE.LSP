;;;;;;eccentric reducer lisp
(defun ere(/ p1 p2 p2sel ang rt piphd2 br-len br-dia p3 p4 p5 p6 p7 p8 p9)
    (pse1)
    (setvar "osmode" 544)
    (setq p1 (getpoint "\n     Select pipe line:[Default = nea point]:"))
    (setvar "osmode" 512)
    (setq p2 (getpoint p1 "\n     Reducer First point:[Default = nea point]:"))
    (setq p2sel(ssget p2))
    (setvar "osmode" 0)
    (SETQ ang (ANGLE P1  P2))
    (p-data1)
    (if (not redtee)(load"c:/ghk/lsp/tee"))
    (redtee)
    (if (= ok 1)
        (progn
            (setq rt(atof br-len))
            (setq piphd2(/ (atof br-dia) 2))
            (setq p3 (polar p2 (+ ang (dtr 90)) piphd))
            (setq p4 (polar p2 (+ ang (dtr 270)) piphd))
            (setq p5 (polar p4 ang red))
            (setq p6 (polar p5 (+ ang (dtr 90)) piphd2))
            (setq p7 (polar p6 (+ ang (dtr 90)) piphd2))
            (setq p8 (polar p2 ang (* 0.7 red)))
            (setq p9 (polar p6 (+ ang (dtr 180)) (* 0.7 red)))
            (if (/= p2sel nil)
                (command "break" p1 "f" p2 p6 )
            )
            (ls2)
            (command "pline" p3 "w" "0" "0" p4 p5 p7 p3 "")
            (command "layer" "s" "1E" "")
            (command "line" p2 p8 "")
            (command "line" p6 p9 "")
            (weld-mark p2)
            (weld-mark p6)
        )
    )
    (pse2)
)
;;;;;;concentric reducer lisp
(defun cre(/ p1 p2 p2sel ang rt piphd2 br-len br-dia p3 p4 p5 p6 p7)
    (pse1)
    (setvar "osmode" 512)
    (setq p1 (getpoint "\n     Select pipe line:[Default = nea point]:"))
    (setvar "osmode" 512)
    (setq p2 (getpoint p1 "\n     Reducer First point:[Default = nea point]:"))
    (setq p2sel(ssget p2))
    (setvar "osmode" 0)
    (SETQ ang(ANGLE P1  P2))
    (p-data1)
    (if (not redtee)(load"c:/ghk/lsp/tee"))
    (redtee)
    (if (= ok 1)
        (progn
            (setq rt(atof br-len))
            (setq piphd2(/ (atof br-dia) 2))
            (setq p3 (polar p2 ang red))
            (setq p4 (polar p2 (+ ang (dtr 270)) piphd))
            (setq p5 (polar p2 (+ ang (dtr 90)) piphd))
            (setq p6 (polar p3 (+ ang (dtr 270)) piphd2))
            (setq p7 (polar p3 (+ ang (dtr 90)) piphd2))
            (if (/= p2sel nil)
                (command "break" p1 "f" p2 p3 )
            )
            (ls2)
            (command "pline" p4 "w" "0" "0" p5 p7 p6 p4 "")
            (command "layer" "s" "1E" "")
            (command "line" p2 p3 "")
            (weld-mark p2)
            (weld-mark p3)
        )
    )
    (pse2)
)
