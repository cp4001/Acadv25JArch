;<<<<<<<<<<<<<<<<<<<<<<<< AUTO CAD LISP >>>>>>>>>>>>>>>>>>>>>>>>>>>>>>>
;~~~~~~~~~~~~~~~~~~~~~~~~GATE VALVE SIDE LISP~~~~~~~~~~~~~~~~~~~~~~~~~~
(defun gatvf(/ a-pip k-pip flglen flgd flgthk hubdia flghd stubl p2sel
               stubl1 stubd vall vall1 vall2 len p1 p2 ang)
    (if (/= job_direc 1)
        (pse1)
    )
    (p-data3)
    (p-data4)
    (cond
        ((= valve-t 1)
            (p-data5 "gatv")
        )
        ((= valve-t 2)
            (p-data5 "glov")
        )
    )
    (setq p2sel nil)
    (if (= val-view nil)(setq val-view 1))
    (if (> vall 1)
        (progn
            (endflgtype)
            (if (= job_direc 1)
                (progn
                    (setq p2 endpoint)
                    (setq ang endang)
                    (setq p2sel(ssget p2))
                )
                (progn
                    (setvar "osmode" 512)
                    (setq p1 (getpoint    "\nSelection point :[Default = nea point]:"))
                    (setvar "osmode" 512)
                    (setq p2 (getpoint p1 "\nSecond point    :[Default = nea point]:"))
                    (setq p2sel(ssget p2))
                    (setvar "osmode" 0)
                    (setq ang (angle p1 p2))
                )
            )
            (if (or (= val-view 1) (= val-view 2) (= val-view 3) (= val-view nil))
                (progn
                    (if (/= p2sel nil)
                        (command "break" p2 (polar p2 ang len))
                    )
                    (command "layer" "s" "1E" "")
                    (command "line" p2 (polar p2 ang len) "")
                    (if (or (= flg_end "F") (= flg_end "W"))
                        (progn
                            (if (not val-flg)(load"c:/ghk/lsp/val-flg"))
                            (val-flg ang p2)
                            (val-flg (+ ang (dtr 180)) (polar p2 ang len))
                        )
                    )
                )
            )
            (if (or (= vall1 nil) (< vall1 1))
                (progn
                    (setq vall1(* vall 2))
                    (setq vall2 vall)
                )
            )
            (gatebase ang p2 p1)
        )
        (prompt "\n    IS NOT SIZE")
    )
    (if (/= job_direc 1)
        (pse2)
    )
)

(defun gatebase(gat-par1 gat-par2 gat-par3 / val_1 val_2 val1 val2 val3 val4
                  h1 h2 h3 h4 h5 h6 h7 h8 h9 h10 h11)
    (if (not valve)(load"c:/ghk/lsp/valve"))
    (cond
        ((= val-view 1)
            (valve gat-par1 gat-par2)
            (gatvf1)
        )
        ((= val-view 2)
            (valve gat-par1 gat-par2)
            (gatvt1)
        )
        ((= val-view 3)
            (valve gat-par1 gat-par2)
            (gatvb1)
        )
        ((= val-view 4)
            (gatvs1)
        )
        ((= val-view 5)
            (gatvh1)
        )
    )
)

(defun gatvf1()
    (command "layer" "s" "2C" "")
    (command "pline" val1 "w" "0" "0" val3 val2 val4 val1 "")
    (setq h1 (polar gat-par2 gat-par1 (/ len 2)))
    (if (= valve-t 1)
        (setq h2 (polar h1 (+ gat-par1 (dtr 90)) (* 0.8 vall1)))
        (setq h2 (polar h1 (+ gat-par1 (dtr 90)) vall1))
    )
    (setq h3 (polar h2 (+ gat-par1 (dtr 90)) (* 0.2 vall1)))
    (setq h4 (polar h2 gat-par1 (/ vall2 2)))
    (setq h5 (polar h4 (+ gat-par1 (dtr 180)) vall2))
    (if (= vall2 vall)
        (progn
            (setq h7 (polar h5 (+ gat-par1 (dtr 90)) 2))
            (setq h8 (polar h7 (+ gat-par1 (dtr 90)) (* 2 s)))
            (setq h9 (polar h8 (+ gat-par1 (dtr 90)) (* 2 s)))
            (setq h10 (polar h8 (+ gat-par1 (dtr 180)) (* 2 s)))
            (setq h11(polar h8 gat-par1 (* 2 s)))
            (command "layer" "s" "1C" "")
            (command "line" h7 h10 h11 h7 "")
            (command "line" h8 h9 "")
        )
    )
    (command "layer" "s" "5C" "")
    (command "line" h4 h5 "")
    (command "layer" "s" "1C" "")
    (command "line" VAL1 h2 VAL2 "")
    (command "line" h1 h2 "")
    (if (= valve-t 1)
        (progn
            (command "layer" "s" "5C" "")
            (command "line" h3 h2 "")
        )
        (progn
            (command "layer" "s" "1C" "")
            (command "donut" "0" (* pipd 0.7) h1 "")
        )
    )
)

(defun gatvb1()
    (command "layer" "s" "2C" "")
    (command "pline" val1 "w" "0" "0" val3 val2 val4 val1 "")
    (command "layer" "s" "2C" "")
    (setq w1 (polar gat-par2 gat-par1 (/ len 2)))
    (setq w2 (polar w1 (+ gat-par1 1.13446) (/ vall2 2)))
    (setq w3 (polar w1 (+ gat-par1 2.00713) (/ vall2 2)))
    (setq w4 (polar w1 (- gat-par1 1.13446) (/ vall2 2)))
    (setq w5 (polar w1 (- gat-par1 2.00713) (/ vall2 2)))
    (if (= vall2 vall)
        (progn
            (setq h7 (polar val3 (+ gat-par1 (dtr 90)) (* s 10)))
            (setq h8 (polar h7 (+ gat-par1 (dtr 90)) (* 2 s)))
            (setq h9 (polar h8 (+ gat-par1 (dtr 90)) (* 2 s)))
            (setq h10 (polar h8 (+ gat-par1 (dtr 180)) (* 2 s)))
            (setq h11(polar h8 gat-par1 (* 2 s)))
            (command "layer" "s" "1C" "")
            (command "line" h7 h10 h11 h7 "")
            (command "line" h8 h9 "")
        )
    )
    (command "arc" "c" w1 w2 w3)
    (command "arc" "c" w1 w5 w4)
    (if (= valve-t 2)
        (progn
            (setq h1 (polar gat-par2 gat-par1 (/ len 2)))
            (command "layer" "s" "1C" "")
            (command "donut" "0" (* pipd 0.7) h1 "")
        )
    )
)

(defun gatvt1()
    (command "layer" "s" "2C" "")
    (command "pline" val1 "w" "0" "0" val3 val2 val4 val1 "")
    (setq h1 (polar gat-par2 gat-par1 (/ len 2)))
    (command "layer" "s" "2C" "")
    (command "circle" h1 "d" vall2)
    (if (= vall2 vall)
        (progn
            (setq h7 (polar val3 (+ gat-par1 (dtr 90)) (* s 10)))
            (setq h8 (polar h7 (+ gat-par1 (dtr 90)) (* 2 s)))
            (setq h9 (polar h8 (+ gat-par1 (dtr 90)) (* 2 s)))
            (setq h10 (polar h8 (+ gat-par1 (dtr 180)) (* 2 s)))
            (setq h11(polar h8 gat-par1 (* 2 s)))
            (command "layer" "s" "1C" "")
            (command "line" h7 h10 h11 h7 "")
            (command "line" h8 h9 "")
        )
    )
    (if (= valve-t 2)
        (progn
            (command "layer" "s" "1C" "")
            (command "donut" "0" (* pipd 0.7) h1 "")
        )
    )
)

(defun gatvh1()
    (setq p3 (polar gat-par3 gat-par1 (/ flgd 2)))
    (setq h1 (polar p3 gat-par1 (- vall1 (/ flgd 2))))
    (setq h2 (polar h1 (- gat-par1 3.14159) (* vall1 0.1)))
    (setq h3 (polar h2 (+ gat-par1 1.5708) (/ vall2 2)))
    (setq h4 (polar h3 (- gat-par1 1.5708) vall2))
    (setq h5 (polar gat-par3 (+ gat-par1 1.5708) flghd))
    (setq h6 (polar gat-par3 (- gat-par1 1.5708) flghd))
    (if (= vall2 vall)
        (progn
            (setq h7 (polar h5 (+ gat-par1 (dtr 90)) s))
            (setq h8 (polar h7 (+ gat-par1 (dtr 90)) (* 2 s)))
            (setq h9 (polar h8 (+ gat-par1 (dtr 90)) (* 2 s)))
            (setq h10 (polar h8 (+ gat-par1 (dtr 180)) (* 2 s)))
            (setq h11(polar h8 gat-par1 (* 2 s)))
            (command "layer" "s" "1C" "")
            (command "line" h7 h10 h11 h7 "")
            (command "line" h8 h9 "")
        )
    )
    (if (= valve-t 1)
        (progn
            (command "layer" "s" "5C" "")
            (command "line" h1 h2 "")
        )
    )
    (command "layer" "s" "5C" "")
    (command "line" h3 h4 "")
    (command "layer" "s" "1C" "")
    (command "line" h5 h2 h6 "")
    (command "line" p3 h2 "")
)

(defun gatvs1()
    (setq p3 (polar gat-par3 gat-par1 (/ flgd 2)))
    (setq h1 (polar p3 gat-par1 (- vall1 (/ flgd 2))))
    (setq h2 (polar h1 (- gat-par1 3.14159) (* vall1 0.1)))
    (setq h3 (polar h2 (+ gat-par1 1.5708) (/ vall2 2)))
    (setq h4 (polar h3 (- gat-par1 1.5708) vall2))
    (setq h5 (polar gat-par3 (+ gat-par1 1.5708) flghd))
    (setq h6 (polar gat-par3 (- gat-par1 1.5708) flghd))
    (if (= vall2 vall)
        (progn
            (setq h7 (polar val3 (+ gat-par1 (dtr 90)) (* s 10)))
            (setq h8 (polar h7 (+ gat-par1 (dtr 90)) (* 2 s)))
            (setq h9 (polar h8 (+ gat-par1 (dtr 90)) (* 2 s)))
            (setq h10 (polar h8 (+ gat-par1 (dtr 180)) (* 2 s)))
            (setq h11(polar h8 gat-par1 (* 2 s)))
            (command "layer" "s" "1C" "")
            (command "line" h7 h10 h11 h7 "")
            (command "line" h8 h9 "")
        )
    )
    (if (= valve-t 1)
        (progn
            (command "layer" "s" "5C" "")
            (command "line" h1 h2 "")
        )
    )
    (command "layer" "s" "5C" "")
    (command "line" h3 h4 "")
    (command "layer" "s" "1C" "")
    (command "line" h5 h2 h6 "")
    (command "line" p3 h2 "")
    (command "layer" "s" "2C" "")
    (command "circle" gat-par3 piphd)
    (command "circle" gat-par3 flghd)
)
