;<<<<<<<<<<<<<<<<<<<<<<<< AUTO CAD LISP >>>>>>>>>>>>>>>>>>>>>>>>>>>>>>>
;~~~~~~~~~~~~~~~~~~~~~~~~CHECK VALVE SIDE LISP~~~~~~~~~~~~~~~~~~~~~~~~~~
(defun flowmate(/ a-pip k-pip flglen flgd flgthk hubdia flghd stubl
                  stubl1 stubd len s1 s2 s3)
    (pse1)
    (p-data3)
    (p-data4)
    (setvar "osmode" 512)
    (setq p1 (getpoint    "\nSelection point :[Default = nea point]:"))
    (setvar "osmode" 512)
    (setq p2 (getpoint p1 "\nSecond point    :[Default = nea point]:"))
    (setq p2sel(ssget p2))
    (setvar "osmode" 0)
    (setq ang (angle p1 p2))
    (setq len(* g 2))
    (setq s1 (polar p2 ang g))
    (setq s2 (polar s1 (+ ang (dtr 270)) piphd))
    (setq s3 (polar s1 (+ ang (dtr 90)) piphd))
    (if (/= p2sel nil)
        (command "break" p1 "f" p2 (polar p2 ang len))
    )
    (command "layer" "s" "1E" "")
    (command "line" p2 (polar p2 ang len) "")
    (if (or (= flg_end "F") (= flg_end "W"))
        (progn
            (if (not val-flg)(load"c:/ghk/lsp/val-flg"))
            (val-flg ang p2)
            (val-flg (+ ang (dtr 180)) (polar p2 ang len))
        )
    )
    (command "layer" "s" "2C" "")
    (command "line" s2 s3 "")
    (pse2)
)
