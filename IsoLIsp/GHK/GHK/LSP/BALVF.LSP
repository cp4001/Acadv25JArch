;<<<<<<<<<<<<<<<<<<<<<<<< AUTO CAD LISP >>>>>>>>>>>>>>>>>>>>>>>>>>>>>>>
;~~~~~~~~~~~~~~~~~~~~~~~~BALL VALVE SIDE LISP~~~~~~~~~~~~~~~~~~~~~~~~~~
(defun balvf(/ a-pip k-pip flglen flgd flgthk hubdia flghd stubl p2sel
               stubl1 stubd vall vall1 vall2 len p1 p2 ang)
    (if (/= job_direc 1)
        (pse1)
    )
    (p-data3)
    (p-data4)
    (p-data5 "ball")
    (if (> vall 1)
        (progn
            (endflgtype)
            (if (= job_direc 1)
                (progn
                    (setq p2 endpoint)
                    (setq ang endang)
                    (setq p2sel(ssget p2))
                )
                (progn
                    (setvar "osmode" 512)
                    (setq p1 (getpoint    "\nSelection point :[Default = nea point]:"))
                    (setvar "osmode" 512)
                    (setq p2 (getpoint p1 "\nSecond point    :[Default = nea point]:"))
                    (setq p2sel(ssget p2))
                    (setvar "osmode" 0)
                    (setq ang (angle p1 p2))
                )
            )
            (if (/= p2sel nil)
                (command "break" p2 (polar p2 ang len))
            )
            (command "layer" "s" "1E" "")
            (command "line" p2 (polar p2 ang len) "")
            (if (or (= flg_end "F") (= flg_end "W"))
                (progn
                    (if (not val-flg)(load"c:/ghk/lsp/val-flg"))
                    (val-flg ang p2)
                    (val-flg (+ ang (dtr 180)) (polar p2 ang len))
                )
            )
            (ballbase ang p2 p1)
        )
        (prompt "\n    IS NOT SIZE")
    )
    (if (/= job_direc 1)
        (pse2)
    )
)

(defun ballbase(bal-par1 bal-par2 bal-par3 / val_1 val_2 val1 val2 val3
                  val4 h1 h2 h3 h4)
    (if (not valve)(load"c:/ghk/lsp/valve"))
    (valve bal-par1 bal-par2)
    (command "layer" "s" "2C" "")
    (command "pline" val1 "w" "0" "0" val3 val2 val4 val1 "")
    (setq h1 (polar bal-par2 bal-par1 (/ len 2)))
    (setq h2 (polar h1 (+ bal-par1 (dtr 90)) (/ pipd 2)))
    (setq h3 (polar h2 (+ bal-par1 (dtr 90)) flghd))
    (setq h4 (polar h3 bal-par1 pipd))
    (command "circle" h1 "d" pipd)
    (command "line" h2 h3 h4 "")
)
