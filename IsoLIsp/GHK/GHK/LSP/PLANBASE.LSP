;;; pipe spacing
(defun c:sp()
    (IF (not space)(load"c:/ghk/lspspace"))(space)
)
;Set no.2
(defun pse1()
    (setq olderr *error* *error* ghkerr)
    (command "cmdecho" "0")
    (dim-scale)
    (face-dim)
    (layer1)
    (graphscr)
    (setq la (getvar "clayer"))
    (setq orth(getvar "orthomode"))
    (setq os(getvar "osmode"))
    (if (= ghk nil)
       (progn
        (setq ghk 150)
        (ch-size ghk)
       )
    )
    (RESETGHK)
    (initget 1)
)

(defun pse2()
    (setq olderr *error* *error* ghkerr)
    (setvar "orthomode" orth)
    (setvar "osmode" os)
    (setvar "clayer" la)
    (setq job_direc nil)
)

(defun face-dim()
    (if (< ghk large)(setq g 0.5)(setq g 0.75))
;    (if (not ga) (setq ga 6) (if (/= ga 6) (setq ga ga)))
    (setq g (* s g))
    (if (< g 50)(setq g g)(setq g 50))
)

(defun resetghk()
(setvar "modemacro" (strcat "Layer:$(substr,$(getvar,clayer),1,8)"
                            (if (= ghk nil) " Unselect Size" (strcat " " (rtos ghk 2 0) "A "))
                            " Rat:"(if (= rat "A") " 150#" (if (= rat "B") " 300#" (if (= rat "C") " 600#" (if (= rat "D") " 900#"))))
                            " Flg:"(if (= sd "S") " SLIP ON" (if (= sd "L") " LAP JOINT" (if (= sd "W") " WELD NECK" (if (= sd "SW") " SOCK WELD" (if (= sd "SCR'D") " SCR'D" sd)))))
                    )
)
)

;Data file read
(defun p-data(file / fn n-line if1)
	(setq lst1 nil lst2 nil)
 
       (setq fn(open (strcat "c:/ghk/lsp/" file".dat") "r"))
       (setq msg(read-line fn))
       (while (setq n-line(read-line fn))
              (setq if1(substr n-line 1 1))
              (cond ((= if1 "*")
                     (setq lst2(cons (substr n-line 2) lst2))
                    )
                    ((= if1 "(")
                     (setq lst1(cons (read n-line) lst1))
                    )
              )
       )
       (setq lst1(reverse lst1) lst2(reverse lst2))
)

(defun p-data1(/ lst1 lst1- sw3 bw)
    (p-data "pipe")
    (if (< S 40)
        (if (< ghk 40)(setq sizenum "3")(ch-size ghk))
        (if (< s 90)
            (if (< ghk 50)(setq sizenum "4")(ch-size ghk))
            (if (< ghk 125)(setq sizenum "8")(ch-size ghk))
        )
    )
    (setq lst1- (nth (atoi sizenum) lst1))
    (if (< ghk sock)
        (progn
            (setq sw3 (nth 1 lst1-))
            (setq elbow90l(atof (nth 0 sw3)) elbow90s(atof (nth 1 sw3)) elbow45(atof (nth 2 sw3))
                  tee(atof (nth 3 sw3)) cplg(atof (nth 4 sw3)) cap(atof (nth 5 sw3))
                  swg(atof (nth 6 sw3)) a-pip(atof (nth 11 sw3)) k-pip(atof (nth 12 sw3))
            )
        )
        (progn
            (setq bw (nth 0 lst1-))
            (setq elbow90l(atof (nth 0 bw)) elbow90s(atof (nth 1 bw)) elbow45(atof (nth 2 bw))
                  tee(atof (nth 3 bw)) red(atof (nth 4 bw)) cap(atof (nth 5 bw)) swg(atof (nth 6 bw))
                  a-pip(atof (nth 10 bw)) k-pip(atof (nth 11 bw))
            )
        )
    )
    (pset1)
)

(defun p-data2(/ lst1 lst1- sw3 bw)
    (p-data "pipe")
    (if (< S 40)
        (if (< ghk 80)(setq sizenum "6")(ch-size ghk))
        (if (< s 90)
            (if (< ghk 100)(setq sizenum "7")(ch-size ghk))
            (if (< ghk 150)(setq sizenum "9")(ch-size ghk))
        )
    )
    (setq lst1- (nth (atoi sizenum) lst1))
    (if (< ghk sock)
        (progn
            (setq sw3 (nth 1 lst1-))
            (setq a-pip(atof (nth 11 sw3)) k-pip(atof (nth 12 sw3)))
        )
        (progn
            (setq bw (nth 0 lst1-))
            (setq a-pip(atof (nth 10 bw)) k-pip(atof (nth 11 bw)))
        )
    )
    (pset1)
)

(defun p-data3(/ lst1 lst1- sw3 bw)
    (p-data "pipe")
    (ch-size ghk)
    (setq lst1- (nth (atoi sizenum) lst1));size select
    (if (< ghk sock)
        (progn
            (setq sw3 (nth 1 lst1-))
            (setq a-pip(atof (nth 11 sw3)) k-pip(atof (nth 12 sw3)))
        )
        (progn
            (setq bw (nth 0 lst1-))
            (setq a-pip(atof (nth 10 bw)) k-pip(atof (nth 11 bw)))
        )
    )
    (pset1)
)

(defun p-data4(/ lst1 lst1- lst10 lst10- lst11 flglen1 flglen2)
    (p-data "flg")
    (ch-size ghk)
    (setq lst1- (nth (atoi sizenum) lst1));size select
    (setq lst10(nth 0 lst1-));WN flg
    (cond
        ((= rat "A")
            (setq lst10-(nth 0 lst10));150#
        )
        ((= rat "B")
            (setq lst10-(nth 1 lst10));300#
        )
        ((= rat "C")
            (setq lst10-(nth 2 lst10));600#
        )
        ((= rat "D")
            (setq lst10-(nth 3 lst10));900#
        )
        ((= rat "E")
            (setq lst10-(nth 4 lst10));1500#
        )
        ((= rat "F")
            (setq lst10-(nth 5 lst10));2500#
        )
    )
    ;     wnf len                      sof len                      flgdia
    (setq flglen1(atof (nth 0 lst10-)) flglen2(atof (nth 1 lst10-)) flgd(atof (nth 2 lst10-))
          flgthk(atof (nth 3 lst10-)) hubdia(atof (nth 4 lst10-)) flghd (/ flgd 2.0)
    )    ;sof wnfthk                  wnfhub
    (if (= sd "W")
        (setq flglen flglen1)
        (setq flglen flglen2)
    )
    (setq lst11(nth 1 lst1-));Stub end
    (setq stubl(atof (nth 0 lst11)) stubl1(atof (nth 1 lst11)) stubd(atof (nth 2 lst11)))
)

(defun p-data5(data1 / lst1 lst1- lst10 lst10-)
    (p-data data1)
    (ch-size ghk)
    (setq lst1- (nth (atoi sizenum) lst1));size select
    (if (/= lst1- nil)
        (pset2)
    )
    (if (or (= lst10- nil) (= lst1- nil))
        (setq vall 0 vall1 0 vall2 0)
        (progn
            (setq vall(atof (nth 0 lst10-)))
            (setq vall1(nth 1 lst10-))
            (if (= vall1 nil)
                (setq vall1 0 vall2 0)
                (setq vall1(atof (nth 1 lst10-)) vall2(atof (nth 2 lst10-)))
            )
        )
    )
    (if (or (= flg_end "F")(= flg_end "W")(= flg_end nil))
        (setq len (+ vall ga))
        (setq len vall)
    )
)

(defun pset1()
 (if (= 1 ks-)
     (progn
      (setq pipd k-pip)
      (setq piphd (/ k-pip 2.0))
     )
     (progn
      (setq pipd a-pip)
      (setq piphd (/ a-pip 2.0))
     )
 )
)

(defun pset2()
    (cond
        ((= flg_end "F")
            (setq lst10(nth 0 lst1-));Flange Type
        )
        ((or (= flg_end "B") (= flg_end "S"))
            (setq lst10(nth 1 lst1-));Sock Type
        )
        ((or (= flg_end "W") (= flg_end "T"))
            (setq lst10(nth 2 lst1-));Wafer Type
        )
    )
    (if (/= lst10 nil)
        (cond
            ((= rat "A")
                (setq lst10-(nth 0 lst10));150#
            )
            ((= rat "B")
                (setq lst10-(nth 1 lst10));300#
            )
            ((= rat "C")
                (setq lst10-(nth 2 lst10));600#
            )
            ((= rat "D")
                (setq lst10-(nth 3 lst10));800# 900#
            )
            ((= rat "E")
                (setq lst10-(nth 4 lst10));1500#
            )
            ((= rat "F")
                (setq lst10-(nth 5 lst10));2500#
            )
        )
    )
)

(defun endflgtype()
    (cond
        ((= flg_end "F")
            (prompt "\n <<<<<  Flange Type  >>>>>")
        )
        ((= flg_end "S")
            (prompt "\n <<<<<  Sock Weld Type  >>>>>")
        )
        ((= flg_end "T")
            (prompt "\n <<<<<  Thred Type  >>>>>")
        )
        ((= flg_end "W")
            (prompt "\n <<<<<  Wafer Type  >>>>>")
        )
        ((= flg_end "B")
            (prompt "\n <<<<<  Butt Weld Type  >>>>>")
        )
    )
)

;Layer set1
(defun ls1()
    (if (< ghk large)(command "layer" "s" "5C" "")
        (if (< ghk double)(command "layer" "s" "8C" "")
            (command "layer" "s" "5C" "")))
)

;Layer set2
(defun ls2()
    (if (< ghk large)
        (command "layer" "s" "3C" "")
        (if (< ghk double)
             (command "layer" "s" "5C" "")
             (command "layer" "s" "5C" "")
        )
    )
)

;Layer set3
(defun ls3()
    (if (< ghk large)
        (command "layer" "s" "2C" "")
        (if (< ghk double)
             (command "layer" "s" "3C" "")
             (command "layer" "s" "5C" "")
        )
    )
)

(defun valset()
    (setq dcl_id (load_dialog "valset.dcl"))
    (if (not old_point)(setq old_point '(640 480)))
    (if (not (new_dialog "valset" dcl_id "" old_point))
        (exit)
    )
    (start_image "image1")
    (slide_image 0 0 (dimx_tile "image1") (dimy_tile "image1")  "c:/ghk/lsp/diatype")
    (end_image)
    (start_image "image2")
    (slide_image 0 0 (dimx_tile "image2") (dimy_tile "image2") "c:/ghk/lsp/buttype")
    (end_image)
    (cond ((= 1 dia-type) (set_tile "zdia1" "1"))
          ((= 2 dia-type) (set_tile "zdia2" "1"))
    )
    (cond ((= 1 but-type) (set_tile "zbut1" "1"))
          ((= 2 but-type) (set_tile "zbut2" "1"))
    )
    (action_tile "accept" "(progn (setq x $x y $y) (setq old_point (done_dialog 1)))")
    (action_tile "zdia1" "(setq dia-type 1)")
    (action_tile "zdia2" "(setq dia-type 2)")
    (action_tile "zbut1" "(setq but-type 1)")
    (action_tile "zbut2" "(setq but-type 2)")
    (setq ok(start_dialog))
    (done_dialog)
    (unload_dialog dcl_id)
    (princ)
)

(defun minpipe()
    (cond
        ((< ghk 66)
            (setq minpip 30)
        )
        ((< ghk 251)
            (setq minpip 50)
        )
        ((< ghk 401)
            (setq minpip 70)
        )
        ((> ghk 402)
            (setq minpip 90)
        )
    )
)
(defun weld-mark(mark1)
    (command "layer" "s" "1C" "")
    (if (< ghk large)
        (command "insert" "c:/ghk/dwg/p-weld1" mark1 weld1 weld1 "0")
        (command "insert" "c:/ghk/dwg/p-weld2" mark1 weld2 weld2 "0")
    )
)
;;;;;;;;;;;;;;;;;;;p1      ang
(defun endconn-flg(endcon1 endcon2 / endpoint endang p4sel)
    (if (= withflg "ON")
        (progn
            (p-data1)
            (p-data4)
            (minpipe)
            (setq p4sel nil)
            (if (= sd "S")
                (setq endpoint(polar endcon1 endcon2 (+ flglen minpip weldc)))
                (if (= sd "L")
                    (setq endpoint(polar endcon1 endcon2 (+ stubl weldc)))
                    (setq endpoint(polar endcon1 endcon2 (+ flglen weldc)))
                )
            )
            (ls1)
            (setq p4sel(ssget endpoint))
            (if (< ghk double)(command "line" endcon1  endpoint ""))
            (setq endang endcon2)
            (if (not val-flg)(load"c:/ghk/lsp/val-flg"))
            (val-flg endang endpoint)
            (if (>= ghk double)
                (val-flg (+ endang (dtr 180)) endpoint)
                (progn
                    (if (/= p4sel nil)
                        (command "break" (polar endpoint endang (* g 1.5)) endpoint)
                    )
                    (command "layer" "s" "1E" "")
                    (command "line" endpoint (polar endpoint endang (* g 1.5)) "")
                    (val-flg (+ endang (dtr 180)) (polar endpoint endang (* g 1.5)))
                )
            )
        )
    )
)

;;;;;;;;;;;;;;;;;;;p1      ang
(defun endconn-val(endcon1 endcon2 / endpoint endang)
    (setq val-view 2)
    (setq job_direc 1)
    (minpipe)
    (if (= sd "S")
        (setq endpoint (polar endcon1 endcon2 (+ flglen minpip  weldc)))
        (if (= sd "L")
            (setq endpoint(polar endcon1 endcon2 (+ stubl weldc)))
            (setq endpoint(polar endcon1 endcon2 (+ flglen weldc)))
        )
    )
    (setq endang endcon2)
    (cond
        ((= withval 1)
            (setq valve-t 1)
            (if (not gatvf)(load"c:/ghk/lsp/gatvf"))
            (gatvf)
        )
        ((= withval 2)
            (setq valve-t 2)
            (if (not gatvf)(load"c:/ghk/lsp/gatvf"))
            (gatvf)
        )
        ((= withval 3)
            (if (not chkvf)(load"c:/ghk/lsp/chkvf"))
            (chkvf)
        )
        ((= withval 4)
            (if (not balvf)(load"c:/ghk/lsp/balvf"))
            (balvf)
        )
        ((= withval 5)
            (if (not diavf)(load"c:/ghk/lsp/diavf"))
            (diavf)
        )
        ((= withval 6)
            (if (not butvf)(load"c:/ghk/lsp/butvf"))
            (butvf)
        )
    )
    (setq withval nil)
)

(defun entt-ch(entt1 / en el c-layer b1)
    (setq en(ssname (ssget "l") 0))
    (setq el(entget en))
    (setq c-layer (assoc 8 el))
    (setq b1 (subst (cons (car c-layer) entt1) c-layer el))
    (entmod b1)
)
(defun entt-ch1(entt1 entt2 entt3 / en el point-1 b1)
    (setq en(ssname entt1 0))
    (setq el(entget en))
    (if (equal entt2 (cdr (assoc 10 el)))
        (setq point-1 (assoc 10 el))
        (if (equal entt2 (cdr (assoc 11 el)))
            (setq point-1 (assoc 11 el))
            (if (equal (angle entt2 entt3) (angle entt2 (cdr (assoc 10 el))))
                (setq point-1 (assoc 11 el))
                (setq point-1 (assoc 10 el))
            )
        )
    )
;    (if (or (equal (angle entt2 entt3) (angle entt2 (cdr (assoc 10 el))))
;            (equal entt2 (cdr (assoc 10 el))))
    (setq b1 (subst (cons (car point-1) entt3) point-1 el))
    (entmod b1)
)
(defun ch-size(i_pnt /)
    (cond
        ((= i_pnt   15)(setq sizenum  "0")(setq chsize "1/2"))
        ((= i_pnt   20)(setq sizenum  "1")(setq chsize "3/4"))
        ((= i_pnt   25)(setq sizenum  "2")(setq chsize "1"))
        ((= i_pnt   40)(setq sizenum  "3")(setq chsize "1 1/2"))
        ((= i_pnt   50)(setq sizenum  "4")(setq chsize "2"))
        ((= i_pnt   65)(setq sizenum  "5")(setq chsize "2 1/2"))
        ((= i_pnt   80)(setq sizenum  "6")(setq chsize "3"))
        ((= i_pnt  100)(setq sizenum  "7")(setq chsize "4"))
        ((= i_pnt  125)(setq sizenum  "8")(setq chsize "5"))
        ((= i_pnt  150)(setq sizenum  "9")(setq chsize "6"))
        ((= i_pnt  200)(setq sizenum "10")(setq chsize "8"))
        ((= i_pnt  250)(setq sizenum "11")(setq chsize "10"))
        ((= i_pnt  300)(setq sizenum "12")(setq chsize "12"))
        ((= i_pnt  350)(setq sizenum "13")(setq chsize "14"))
        ((= i_pnt  400)(setq sizenum "14")(setq chsize "16"))
        ((= i_pnt  450)(setq sizenum "15")(setq chsize "18"))
        ((= i_pnt  500)(setq sizenum "16")(setq chsize "20"))
        ((= i_pnt  550)(setq sizenum "17")(setq chsize "22"))
        ((= i_pnt  600)(setq sizenum "18")(setq chsize "24"))
        ((= i_pnt  650)(setq sizenum "19")(setq chsize "26"))
        ((= i_pnt  700)(setq sizenum "20")(setq chsize "28"))
        ((= i_pnt  750)(setq sizenum "21")(setq chsize "30"))
        ((= i_pnt  800)(setq sizenum "22")(setq chsize "32"))
        ((= i_pnt  850)(setq sizenum "23")(setq chsize "34"))
        ((= i_pnt  900)(setq sizenum "24")(setq chsize "36"))
        ((= i_pnt  950)(setq sizenum "25")(setq chsize "38"))
        ((= i_pnt 1000)(setq sizenum "26")(setq chsize "40"))
        ((= i_pnt 1050)(setq sizenum "27")(setq chsize "42"))
        ((= i_pnt 1100)(setq sizenum "28")(setq chsize "44"))
        ((= i_pnt 1150)(setq sizenum "29")(setq chsize "46"))
        ((= i_pnt 1200)(setq sizenum "30")(setq chsize "48"))
        ((= i_pnt 1250)(setq sizenum "31")(setq chsize "50"))
        ((= i_pnt 1300)(setq sizenum "32")(setq chsize "52"))
        ((= i_pnt 1350)(setq sizenum "33")(setq chsize "54"))
        ((= i_pnt 1400)(setq sizenum "34")(setq chsize "56"))
        ((= i_pnt 1450)(setq sizenum "35")(setq chsize "58"))
        ((= i_pnt 1500)(setq sizenum "36")(setq chsize "60"))
        ((= i_pnt 1650)(setq sizenum "37")(setq chsize "66"))
        ((= i_pnt 1800)(setq sizenum "38")(setq chsize "72"))
        ((= i_pnt   10)(setq sizenum "39")(setq chsize "3/8"))
    )
)

(defun ch-size1(i_pnt /)
    (cond
        ((= i_pnt "1/2"  )(setq n-len1  "015"))
        ((= i_pnt "3/4"  )(setq n-len1  "020"))
        ((= i_pnt "1"    )(setq n-len1  "025"))
        ((= i_pnt "1 1/2")(setq n-len1  "040"))
        ((= i_pnt "2"    )(setq n-len1  "050"))
        ((= i_pnt "2 1/2")(setq n-len1  "065"))
        ((= i_pnt "3"    )(setq n-len1  "080"))
        ((= i_pnt "4"    )(setq n-len1  "100"))
        ((= i_pnt "5"    )(setq n-len1  "125"))
        ((= i_pnt "6"    )(setq n-len1  "150"))
        ((= i_pnt "8"    )(setq n-len1  "200"))
        ((= i_pnt "10"   )(setq n-len1  "250"))
        ((= i_pnt "12"   )(setq n-len1  "300"))
        ((= i_pnt "14"   )(setq n-len1  "350"))
        ((= i_pnt "16"   )(setq n-len1  "400"))
        ((= i_pnt "18"   )(setq n-len1  "450"))
        ((= i_pnt "20"   )(setq n-len1  "500"))
        ((= i_pnt "22"   )(setq n-len1  "550"))
        ((= i_pnt "24"   )(setq n-len1  "600"))
        ((= i_pnt "26"   )(setq n-len1  "650"))
        ((= i_pnt "28"   )(setq n-len1  "700"))
        ((= i_pnt "30"   )(setq n-len1  "750"))
        ((= i_pnt "32"   )(setq n-len1  "800"))
        ((= i_pnt "34"   )(setq n-len1  "850"))
        ((= i_pnt "36"   )(setq n-len1  "900"))
        ((= i_pnt "38"   )(setq n-len1  "950"))
        ((= i_pnt "40"   )(setq n-len1 "1000"))
        ((= i_pnt "42"   )(setq n-len1 "1050"))
        ((= i_pnt "44"   )(setq n-len1 "1100"))
        ((= i_pnt "46"   )(setq n-len1 "1150"))
        ((= i_pnt "48"   )(setq n-len1 "1200"))
        ((= i_pnt "50"   )(setq n-len1 "1250"))
        ((= i_pnt "52"   )(setq n-len1 "1300"))
        ((= i_pnt "54"   )(setq n-len1 "1350"))
        ((= i_pnt "56"   )(setq n-len1 "1400"))
        ((= i_pnt "58"   )(setq n-len1 "1450"))
        ((= i_pnt "60"   )(setq n-len1 "1500"))
        ((= i_pnt "66"   )(setq n-len1 "1650"))
        ((= i_pnt "72"   )(setq n-len1 "1800"))
        ((= i_pnt "3/8"  )(setq n-len1 "010"))
    )
)

(setq WELD1 (* S 0.9))
(setq WELD2 (* S 1.3))
(setq WELD3 (* S 0.5))
(if (< s 35)
    (progn
        (setq sock  50)
        (setq large 80)
        (setq double 300)
    )
    (if (< s 55)
        (progn
            (setq sock  50)
            (setq large 100)
            (setq double 350)
        )
        (if (< s 105)
            (progn
                (setq sock  50)
                (setq large 150)
                (setq double 400)
            )
            (progn
                (setq sock  50)
                (setq large 200)
                (setq double 400)
            )
        )
    )
)
(if (not rat)(setq rat "A"))
(if (not sd)(setq sd "S"))
(if (not flg-type)(setq flg-type 1))
(if (not flg_end)(setq flg_end "F"))
(if (not ga) (setq ga 6))
(if (not weldc) (setq weldc 3))
