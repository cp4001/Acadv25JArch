;<<<<<<<<<<<<<<<<<<<<<<<< AUTO CAD LISP >>>>>>>>>>>>>>>>>>>>>>>>>>>>>>>
;~~~~~~~~~~~~~~~~~~~~~~~~BALL VALVE SIDE LISP~~~~~~~~~~~~~~~~~~~~~~~~~~
(defun butvf(/ a-pip k-pip flglen flgd flgthk hubdia flghd stubl p2sel
               stubl1 stubd vall vall1 vall2 len p1 p2 ang)
    (if (/= job_direc 1)
        (pse1)
    )
    (p-data3)
    (p-data4)
    (p-data5 "butva")
    (if (= but-type nil)(setq but-type 1))
    (if (> vall 1)
        (progn
            (endflgtype)
            (if (= job_direc 1)
                (progn
                    (setq p2 endpoint)
                    (setq ang endang)
                    (setq p2sel(ssget p2))
                )
                (progn
                    (setvar "osmode" 512)
                    (setq p1 (getpoint    "\nSelection point :[Default = nea point]:"))
                    (setvar "osmode" 512)
                    (setq p2 (getpoint p1 "\nSecond point    :[Default = nea point]:"))
                    (setq p2sel(ssget p2))
                    (setvar "osmode" 0)
                    (setq ang (angle p1 p2))
                )
            )
            (if (/= p2sel nil)
                (command "break" p2 (polar p2 ang len))
            )
            (command "layer" "s" "1E" "")
            (command "line" p2 (polar p2 ang len) "")
            (if (or (= flg_end "F") (= flg_end "W"))
                (progn
                    (if (not val-flg)(load"c:/ghk/lsp/val-flg"))
                    (val-flg ang p2)
                    (val-flg (+ ang (dtr 180)) (polar p2 ang len))
                )
            )
            (butbase ang p2 p1)
        )
        (prompt "\n    IS NOT SIZE")
    )
    (if (/= job_direc 1)
        (pse2)
    )
)
;;;;;;;;;;;;;;;ang      p2       p1
(defun butbase(but-par1 but-par2 but-par3 / val1 val2 val3 val4 val5 val6)
    (setq val1 (polar but-par2 but-par1 g))
    (setq val2 (polar val1 (+ but-par1 (dtr 90)) piphd))
    (setq val3 (polar val2 but-par1 (- len (* 2 g))))
    (setq val4 (polar val3 (+ but-par1 (dtr 270)) pipd))
    (setq val5 (polar val4 (+ but-par1 (dtr 180)) (- len (* 2 g))))
    (setq val6 (polar but-par2 but-par1 (/ len 2)))
    (command "layer" "s" "2C" "")
    (if (= 1 but-type)
        (command "pline" val3 "w" "0" "0" val2 val5 val4 val3 val5 "")
        (command "line" val3 val5 "")
    )
    (command "layer" "s" "1C" "")
    (command "donut" "0" (* s 0.8) val6 "")
)
