;;;;;;;gate + strainer valve lisp
(defun gatstrvf(/ a-pip k-pip flglen flgd flgthk hubdia flghd stubl
               stubl1 stubd vall vall1 vall2 g_len s_len len os p1 p2 ang
               val_1 val1 val2 val3 val4 h1 h2 str1 str11 str111 str1111
               str2 str21 str211 str2111 str3 str31 str4 str41 str50
               str5 str51 str511 str512 str513 str6 str61 str62 str63)
    (pse1)
    (p-data3)
    (p-data4)
    (p-data5 "gatv")
    (setq g_len len)
    (p-data5 "y-str")
    (setq s_len len)
    (setq len (+ g_len s_len))
    (setvar "blipmode" 0)
    (setq os (getvar "osmode"))
    (setvar "osmode" 512)
    (setq p1 (getpoint    "\nSelection point :[Default = nea point]:"))
    (setvar "osmode" 512)
    (setq p2 (getpoint p1 "\nSecond point    :[Default = nea point]:"))
    (setvar "osmode" 0)
    (setq ang (angle p1 p2))
    (if (or (= flg_end "F") (= flg_end "W"))
        (progn
            (if (not val-flg)(load"c:/ghk/lsp/val-flg"))
            (val-flg ang p2)
            (val-flg (+ ang (dtr 180)) (polar p2 ang len))
        )
    )
;<<<<<<<<<<<<<<<<<<<<<valve dwg
(setq val_1 (polar p2 (+ ang (dtr 90)) flghd))
(setq val1 (polar val_1 ang g))
(setq val2 (polar val1 ang (- (+ gatl 4.5)(* g 1.5))))
(setq val3 (polar val1 (+ ang (dtr 270)) flgd))
(setq val4 (polar val2 (+ ang (dtr 270)) flgd))
(setq h1 (polar val1 (+ ang (dtr 270)) flghd))
(setq h2 (polar h1 ang (/ (- (+ gatl 4.5)(* g 1.5)) 2)))
(setq str1 (polar val2 ang g))
(setq str11 (polar str1 ang wnfthk))
(setq str111 (polar str11 (+ ang (dtr 270)) (- flghd piphd)))
(setq str1111 (polar str111 (+ ang (dtr 270)) pipd ))
(setq str2 (polar val1 ang (- len (* g 2))))
(setq str21 (polar str2 (+ ang (dtr 180)) wnfthk))
(setq str211 (polar str21 (+ ang (dtr 270)) (- flghd piphd)))
(setq str2111 (polar str211 (+ ang (dtr 270)) pipd ))
(setq str3 (polar str2 (+ ang (dtr 270)) flgd))
(setq str31 (polar str3 (+ ang (dtr 180)) wnfthk))
(setq str4 (polar str1 (+ ang (dtr 270)) flgd))
(setq str41 (polar str4 ang wnfthk))
(setq str50 (polar str1 (+ ang (dtr 270)) flghd))
(setq str5 (polar str50 ang (* pipd 1.5)))
(setq str51 (polar str5 ang (* wnfthk 0.7)))
(setq str511 (polar str51 ang (* wnfthk 0.7)))
(setq str512 (polar str511 (+ ang (dtr 90)) (* flghd 1.3)))
(setq str513 (polar str511 (+ ang (dtr 270)) (* flghd 1.3)))
(setq str6 (polar str5 (+ ang (dtr 270)) flghd))
(setq str61 (polar str5 (+ ang (dtr 90)) flghd))
(setq str62 (polar str511 (+ ang (dtr 270)) flghd))
(setq str63 (polar str511 (+ ang (dtr 90)) flghd))
(setq ang (rtd ang))
(command "layer" "s" "2C" "")
(command "circle" h2 "d" gatw)
(command "pline" val1 "w" "0" "0" val3 val2 val4 val1 "")
(command "line" str1 str11 str41 str4 str1 "")
(command "line" str2 str21 str31 str3 str2 "")
(command "line" str111 str211 "")
(command "line" str1111 str2111 "")
(command "line" str6 str62 "")
(command "line" str61 str63 "")
(command "layer" "s" "1E" "")
(command "line" str512 str513 "")
(command "insert" "*c:/ghk/dwg/flg45" str511 flghd (+ ang (dtr 180)))
(command "insert" "*c:/ghk/dwg/45dnd" str51 flghd (+ ang (dtr 180)))
(command "insert" "*c:/ghk/dwg/45dnd" str5 flghd (+ ang (dtr 180)))
(command "layer" "s" la "")
(setvar "osmode" os)
(setq *error* olderr olderr nil)
(prin1)
)
