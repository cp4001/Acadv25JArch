;; Name   : Pipe
;; Date   : 1997. 1. 22
;; By     : Kim Gihun, Kiryung eng'g CO., LTD.
;; Subject: turn,
;;;;;;Front 90elbow turn lisp ( C2 )
(defun turn(/ p1 p2 p3 ang ang1)
    (pse1)
    (setvar "osmode" 32)
    (setq p1 (getpoint        "\n     Elbow end point:[Default = int point]:"))
    (setvar "osmode" 0)
    (setq p2 (getpoint p1 "\n     First pipe line:[Default = nea point]:"))
    (setvar "osmode" 0)
    (setq p3 (getpoint p1 "\n     Second pipe line:[Default = nea point]:"))
    (SETQ ang (ANGLE p1 p2))
    (SETQ ang1(ANGLE p1 p3))
    (turn1 p1 ang ang1)
    (pse2)
);;;;;;;;;;;;;p1    ang    ang1
(defun turn1(elbow1 elbow2 elbow3 );/ p2sel p3sel elbow90 p4 p5 p6 p7 p8
                                   ; p9 p10 p11 p12)
    (setq p1 elbow1)
    (setvar "osmode" 0)
    (p-data1)
    (if (= radu- "S")(setq elbow90 elbow90s)(setq elbow90 elbow90l))
    (setq p2sel nil)
    (setq p3sel nil)
    (setq p4 (polar p1 elbow2 elbow90));;;p2sel
    (setq p5 (polar p1 elbow3 elbow90));;;p3sel
    (setq p2sel(ssget p4))
    (setq p3sel(ssget p5))
    (setq p6 (polar p4 elbow3 piphd))
    (setq p7 (polar p4 (+ elbow3 (dtr 180)) piphd))
    (setq p8 (polar p5 (+ elbow2 (dtr 180)) piphd))
    (setq p9 (polar p5 elbow2 piphd))
    (setq p10(polar p6 (+ elbow2 (dtr 180)) (- elbow90 piphd)))
    (setq p11(polar p7 (+ elbow2 (dtr 180)) (+ elbow90 piphd)))
    (setq p12(polar p4 (+ elbow2 (dtr 270)) elbow90))
    (if (>= ghk sock)
        (progn
            (if (/= p2sel nil)(entt-ch1 p2sel p1 p4))
            (if (/= p3sel nil)(entt-ch1 p3sel p1 p5))
        )
    )
    (ls1)
    (cond
        ((< ghk sock)
            (command "line" p6 p7 "")
            (command "line" p8 p9 "")
        )
        ((< ghk double)
            (if (< ghk large)
                (setvar "clayer" "5c")
                (setvar "clayer" "8c")
            )
            (command "arc" p4 "e" p5 "d" p1)
            (weld-mark p4)
            (weld-mark p5)
        )
        ((>= ghk double)
            (command "arc" p7 "e" p8 "d" p11)
            (command "arc" p6 "e" p9 "d" p10)
            (command "line" p7 p6 "")
            (command "line" p8 p9 "")
            (setvar "clayer" "1e")
            (command "arc" p4 "e" p5 "d" p1)
        )
    )
    (if (/= withval nil)
        (progn
            (setq endang (getangle p1 "\n     Valve Direction : "))
            (cond
                ((= elbow2 endang)
                    (endconn-val p4 endang)
                    (endconn-flg p5 elbow3)
                )
                ((= elbow3 endang)
                    (endconn-val p5 endang)
                    (endconn-flg p4 elbow2)
                )
            )
        )
        (progn
            (endconn-flg p4 elbow2)
            (endconn-flg p5 elbow3)
        )
    )
)
;;;;;;Front double 90elbow turn lisp ( C-1 )
(defun dturn(/ p1 p2 ang)
    (pse1)
    (setvar "osmode" 32)
    (setq p1 (getpoint    "\n     Elbow end point:[Default = int point]:"))
    (setvar "osmode" 512)
    (setq p2 (getpoint p1 "\n     First pipe line:[Default = nea point]:"))
    (SETQ ang(ANGLE P1 P2))
    (dturn1 p1 p2 ang)
    (pse2)
)          ;;;p1     p2     ang
(defun dturn1(elbow1 elbow2 elbow3 / elbow p3 p4 p5 p6 p7 p8 p9)
    (setvar "osmode" 0)
    (p-data1)
    (if (= radu- "S")(setq elbow90 elbow90s)(setq elbow90 elbow90l))
    (setq p3 (polar elbow1 elbow3 elbow90))
    (setq p4 (polar elbow1 (+ elbow3 (dtr 270)) elbow90))
    (setq p5 (polar p3 (+ elbow3 (dtr 270)) elbow90))
    (setq p6 (polar p3 (+ elbow3 (dtr 90)) piphd))
    (setq p7 (polar p3 (+ elbow3 (dtr 270)) piphd))
    (setq p8 (polar p4 elbow3 piphd))
    (setq p9 (polar p4 (+ elbow3 (dtr 180)) piphd))
    (ls1)
    (command "arc" "c" p5 p7 p9)
    (command "arc" "c" p5 p6 p8)
    (command "line" p6 p7 "")
    (command "line" p8 p9 "")
    (setvar "clayer" "1e")
    (command "arc" "c" p5 p3 p4)
)
;;;;;;pipe 90elbow down lisp ( D-1 )
(defun peldn();(/ p1 p2 p3 ang ang1)
    (pse1)
    (setvar "osmode" 33)
    (setq p1 (getpoint        "\n     Elbow end point:[Default = int point]:"))
    (setvar "osmode" 0)
    (setq p2 (getpoint p1 "\n     First pipe line:[Default = nea point]:"))
    (setvar "osmode" 0)
    (setq p3 (getpoint p1 "\n     Second pipe line:[Default = nea point]:"))
    (SETQ ang (ANGLE p1 p2))
    (SETQ ang1(ANGLE p1 p3))
    (peldn1 p1 ang ang1)
    (pse2)
);;;;;;;;;;;;;p1     ang    ang1
(defun peldn1(elbow1 elbow2 elbow3); / p2sel p3sel elbow p4 p5 p6 p7
;              p8 p9 p10 p11 p12 p13 p14 p15 p16)
    (setvar "osmode" 0)
    (p-data1)
    (setq p2sel nil)
    (setq p3sel nil)
    (if (= radu- "S")(setq elbow90 elbow90s)(setq elbow90 elbow90l))
    (setq p4 (polar elbow1 elbow2 elbow90))
    (setq p5 (polar elbow1 (+ elbow2 (dtr 45)) piphd))
    (setq p6 (polar elbow1 (+ elbow2 (dtr 315)) piphd))
    (setq p7 (polar elbow1 (+ elbow2 (dtr 90)) piphd))
    (setq p8 (polar elbow1 (+ elbow2 (dtr 270)) piphd))
    (setq p9 (polar p4 (+ elbow2 (dtr 90)) piphd))
    (setq p10 (polar p4 (+ elbow2 (dtr 270)) piphd))
    (setq p11 (polar elbow1 (+ elbow2 (dtr 180)) (* piphd 1.3)))
    (setq p12 (polar elbow1 (+ elbow2 (dtr 270)) (* piphd 1.3)))
    (setq p13 (polar elbow1 (+ elbow2 (dtr 90)) (* piphd 1.3)))
    (setq p14 (polar elbow1 elbow3 elbow90))
    (setq p15 (polar p14 (+ elbow3 (dtr 90)) piphd))
    (setq p16 (polar p14 (+ elbow3 (dtr 270)) piphd))
    (setq p2sel(ssget p4))
    (setq p3sel(ssget p14))
    (ls1)
    (cond
        ((< ghk sock)
            (if (/= elbow2 elbow3)
                (progn
                    (command "line" p15 p16 "")
                    (if (= p3sel nil)
                        (command "line" (polar elbow1 elbow3 piphd) p14 "")
                        (if (or (/= (- (rtd elbow2) (rtd elbow3)) 180)
                            (/= (- (rtd elbow2) (rtd elbow3)) -180))
                            (entt-ch1 p3sel elbow1 (polar elbow1 elbow3 piphd))
                        )
                    )
                )
            )
            (if (= p2sel nil)
                (command "line" elbow1 p4 "")
                (if (or (= (- (rtd elbow2) (rtd elbow3)) 180)
                    (= (- (rtd elbow2) (rtd elbow3)) -180))
                    (command "break" elbow1 (polar elbow1 elbow3 piphd))
                    (entt-ch1 p2sel elbow1 elbow1)
                )
            )
            (command "line" p9 p10 "")
            (setvar "clayer" "3c")
            (command "arc" "c" elbow1 p5 p6)
        )
        ((< ghk double)
            (if (= p2sel nil)
                (command "line" elbow1 p4 "")
                (if (or (= (- (rtd elbow2) (rtd elbow3)) 180)
                    (= (- (rtd elbow2) (rtd elbow3)) -180))
                    (command "break" elbow1 (polar elbow1 elbow3 piphd))
                    (entt-ch1 p2sel elbow1 elbow1)
                )
            )
            (weld-mark p4)
            (if (/= elbow2 elbow3)
                (progn
                    (weld-mark p14)
                    (if (< ghk large)
                        (setvar "clayer" "5c")
                        (setvar "clayer" "8c")
                    )
                    (if (= p3sel nil)
                        (command "line" (polar elbow1 elbow3 piphd) p14 "")
                        (if (or (/= (- (rtd elbow2) (rtd elbow3)) 180)
                            (/= (- (rtd elbow2) (rtd elbow3)) -180))
                            (entt-ch1 p3sel elbow1 (polar elbow1 elbow3 piphd))
                        )
                    )
                )
            )
            (if (< ghk large)
                (setvar "clayer" "3c")
                (setvar "clayer" "5c")
            )
            (command "arc" "c" elbow1 p5 p6)
        )
        ((>= ghk double)
            (command "arc" "c" elbow1 p7 p8)
            (command "line" p7 p9 p10 p8 "")
            (if (/= elbow2 elbow3)
                (command "line" (polar elbow1 (+ elbow2 (dtr 180)) piphd) p16 p15 (polar p15 (+ elbow3 (dtr 180)) (- elbow90 piphd)) "")
            )
        )
    )
    (setvar "clayer" "1e")
    (command "line" elbow1 p11 "")
    (command "line" p12 p13 "")
    (if (/= withval nil)
        (if (/= elbow2 elbow3)
            (progn
                (setq endang (getangle p1 "\n     Valve Direction : "))
                (cond
                    ((= elbow2 endang)
                        (endconn-val p4 endang)
                        (endconn-flg p14 elbow3)
                    )
                    ((= elbow3 endang)
                        (endconn-val p14 endang)
                        (endconn-flg p4 elbow2)
                    )
                )
            )
            (endconn-val p4 elbow2)
        )
        (progn
            (endconn-flg p4 elbow2)
            (if (/= elbow2 elbow3)
                (endconn-flg p14 elbow3)
            )
        )
    )
)
;;;;;;Front 45elbow down lisp ( C-5 type 1 , C-6 type 2 )
(defun p45el(/ p1 p2 ang)
    (pse1)
    (setvar "osmode" 32)
    (setq p1 (getpoint "\n     Elbow end point:[Default = int point]:"))
    (setvar "osmode" 512)
    (setq p2 (getpoint p1 "\n     First pipe line:[Default = nea point]:"))
    (SETQ ang (ANGLE P1 P2))
    (p45el1 p1 ang)
    (pse2)
);;;;;;;;;;;;;p1     ang
(defun p45el1(elbow1 elbow2 / p1sel in-ang con p11 p12 p3 p31 p32 p4 p5 p6 p7)
    (setvar "osmode" 0)
    (SETQ in-ang (rtd elbow2))
    (p-data1)
    (setq p1sel(ssget elbow1))
    (setq con 0.707107)
    (setq p11 (polar elbow1 (+ elbow2 (dtr 90)) (* piphd 0.2)))
    (setq p12 (polar elbow1 (+ elbow2 (dtr 270)) (* piphd 0.2)))
    (cond
        ((= p45el-t 1)
            (setq p3 (polar elbow1 (+ elbow2 (dtr 180)) (* con elbow45)))
            (setq p4 (polar elbow1 elbow2 elbow45))
        )
        ((= p45el-t 2)
            (setq p3  (polar elbow1 elbow2 (* con elbow45)))
            (setq p4  (polar elbow1 (+ elbow2 (dtr 180)) elbow45))
        )
    )
    (setq p31 (polar p3 (+ elbow2 (dtr 90)) (* piphd 1.3)))
    (setq p32 (polar p3 (+ elbow2 (dtr 270)) (* piphd 1.3)))
    (setq p5 (polar p3 (+ elbow2 (dtr 180)) (* con piphd)))
    (setq p6 (polar p4 (+ elbow2 (dtr 90)) piphd))
    (setq p7 (polar p4 (+ elbow2 (dtr 270)) piphd))
    (ls1)
    (cond
        ((< ghk sock)
            (command "layer" "s" "5c" "")
            (if (= p1sel nil)
                (command "line" p3 p4 "")
                (command "break" p4 "f" p3 p5)
            )
            (command "insert" "*c:/ghk/dwg/45dn" p3 piphd in-ang)
            (entt-ch "3C")
            (command "layer" "s" "2c" "")
            (command "line" p11 p12 "")
            (command "layer" "s" "5c" "")
            (command "line" p6 p7 "")
        )
        ((< ghk double)
            (command "layer" "s" "8c" "")
            (if (= p1sel nil)
                (command "line" p3 p4 "")
                (command "break" p4 "f" p3 p5)
            )
            (command "insert" "*c:/ghk/dwg/45dn" p3 piphd in-ang)
            (if (< ghk large)
                (entt-ch "3C")
                (entt-ch "5C")
            )
            (command "layer" "s" "2c" "")
            (command "line" p11 p12 "")
            (weld-mark p4)
        )
        ((> ghk double)
            (command "insert" "*c:/ghk/dwg/45dnd" p3 piphd in-ang)
            (entt-ch "5C")
            (setvar "clayer" "2c")
            (command "line" p11 p12 "")
            (setvar "clayer" "5c")
            (command "line" (polar p3 (+ elbow2 (dtr 90)) piphd) p6 p7 (polar p3 (+ elbow2 (dtr 270)) piphd) "")
        )
    )
    (command "layer" "s" "1E" "")
    (command "line" p3 p5 "")
    (command "line" p31 p32 "")
    (if (= p45el-t 1)
        (endconn-flg p4 elbow2)
        (endconn-flg p4 (+ elbow2 (dtr 180)))
    )
    (setq p45el-t nil)
)
;;;;;;Front 45elbow turn lisp ( C-3 type 1 , C-4 type 2)
(defun pel45(/ p1 p2 ang p2sel elbow en el point-1 b1 p4 p41 p42 p5 p51 p52 p55 p6)
    (pse1)
    (setvar "osmode" 1)
    (setq p1 (getpoint "\n     Elbow end point:[Default = end point]:"))
    (setvar "osmode" 512)
    (setq p2 (getpoint p1 "\n     First pipe line:[Default = nea point]:"))
    (SETQ ang (ANGLE P1 P2))
    (pel451 p1 ang)
    (pse2)
);;;;;;;;;;;;;p1     ang
(defun pel451(elbow1 elbow2 / p2sel elbow en el point-1 b1 p4 p41 p42 p5 p51 p52 p55 p6)
    (setvar "osmode" 0)
    (p-data1)
    (if (= radu- "S")(setq elbow90 elbow90s)(setq elbow90 elbow90l))
    (setq p2sel nil)
    (cond
        ((= pel45-t 1)
            (setq p4 (polar elbow1 elbow2 elbow45))
            (setq p2sel(ssget p4))
            (setq p41 (polar p4 (+ elbow2 (dtr 270)) piphd))
            (setq p42 (polar p4 (+ elbow2 (dtr 90)) piphd))
            (setq p5 (polar elbow1 (+ elbow2 (dtr 225)) elbow45))
            (setq p51 (polar p5 (+ elbow2 (dtr 315)) piphd))
            (setq p52 (polar p5 (+ elbow2 (dtr 135)) piphd))
            (setq p55 (polar p5 (+ elbow2 (dtr 225)) piphd))
            (setq p6 (polar p4 (+ elbow2 (dtr 270)) elbow90))
        )
        ((= pel45-t 2)
            (setq p5 (polar elbow1 elbow2 elbow45))
            (setq p2sel(ssget p5))
            (setq p51 (polar p5 (+ elbow2 (dtr 270)) piphd))
            (setq p52 (polar p5 (+ elbow2 (dtr 90)) piphd))
            (setq p4 (polar elbow1 (+ elbow2 (dtr 135)) elbow45))
            (setq p41 (polar p4 (+ elbow2 (dtr 45)) piphd))
            (setq p42 (polar p4 (+ elbow2 (dtr 225)) piphd))
            (setq p45 (polar p4 (+ elbow2 (dtr 135)) piphd))
            (setq p6 (polar  p5 (+ elbow2 (dtr 90)) elbow90))
        )
    )
    (if (and (> ghk sock) (/= p2sel nil))
        (if (= pel45-t 1)
            (entt-ch1 p2sel elbow1 p4)
            (entt-ch1 p2sel elbow1 p5)
        )
    )
    (ls1)
    (cond
        ((< ghk sock)
            (if (= pel45-t 1)
                (command "line" elbow1 p55 "")
                (command "line" elbow1 p45 "")
            )
            (command "line" p41 p42 "")
            (command "line" p51 p52 "")
        )
        ((< ghk double)
            (command "arc" p4 "e" p5 "r" elbow90)
            (weld-mark p4)
            (weld-mark p5)
        )
        ((>= ghk double)
            (command "arc" "c" p6 p41 p51)
            (command "arc" "c" p6 p42 p52)
            (command "line" p41 p42 "")
            (command "line" p51 p52 "")
            (command "layer" "s" "1E" "")
            (command "arc" "c" p6 p4 p5)

        )
    )
    (if (= pel45-t 1)
        (progn
            (endconn-flg p4 elbow2)
            (endconn-flg p5 (+ elbow2 (dtr 225)))
        )
        (progn
            (endconn-flg p5 elbow2)
            (endconn-flg p4 (+ elbow2 (dtr 135)))
        )
    )
    (setq pel45-t nil)
)
;;;;;;pipe 90elbow TO 45down lisp ( B-5 type 1 , B-6 type 2 )
(defun peldn45(/ p1 p2 p4sel p6sel con elbow scale s1 s2 ang ang1 p3 p31 p32 p4 p5 p6)
    (pse1)
    (setvar "osmode" 32)
    (setq p1 (getpoint "\n     Elbow end point:[Default = int point]:"))
    (setvar "osmode" 512)
    (setq p2 (getpoint p1 "\n     Select pipe line:[Default = nea point]:"))
    (setvar "osmode" 0)
    (p-data1)
    (if (= radu- "S")(setq elbow90 elbow90s)(setq elbow90 elbow90l))
    (setq con 0.707107)
    (setq p4sel nil)
    (setq p6sel nil)
    (setq scale (* elbow90 0.707107))
    (setq s1 (- elbow90 piphd))
    (setq s2 (+ elbow90 piphd))
    (SETQ ang (ANGLE P1 P2))
    (SETQ ang1 (rtd ang))
    (if (= peldn45-t 1)
        (setq p3 (polar p1 ang (* con elbow90)))
        (setq p3 (polar p1 (+ ang (dtr 180)) (* con elbow90)))
    )
    (setq p31 (polar p3 (+ ang (dtr 270)) (* piphd 1.5)))
    (setq p32 (polar p3 (+ ang (dtr 90)) (* piphd 1.5)))
    (setq p4 (polar p1 (+ ang (dtr 270)) elbow90))
    (setq p5 (polar p4 ang (* con elbow90)))
    (if (= peldn45-t 1)
        (setq p6 (polar p3 ang (* piphd 0.707107)))
        (setq p6 (polar p3 (+ ang (dtr 180)) (* piphd 0.707107)))
    )
    (setq p4sel(ssget p4))
    (setq p6sel(ssget p6))
    (ls1)
    (if (< ghk double)
        (progn
            (if (/= p4sel nil)(command "break" p4 "f" p4 p1))
            (if (/= p6sel nil)(command "break" p6 "f" p6 p1))
            (if (= peldn45-t 1)
                (command "insert" "*c:/ghk/dwg/90to45" p5 elbow90 ang1)
                (command "insert" "*c:/ghk/dwg/90to45a" p1 elbow90 ang1)
            )
            (entt-ch "8C")
            (if (= peldn45-t 1)
                (command "insert" "*c:/ghk/dwg/45dn" p3 piphd (+ ang1 180))
                (command "insert" "*c:/ghk/dwg/45dn" p3 piphd ang1)
            )
            (entt-ch "5C")
            (command "layer" "s" "1e" "")
            (command "line" p31 p32 "")
            (command "line" p3 p6 "")
            (weld-mark p4)
        )
        (progn
            (if (/= p4sel nil)(command "break" p4 "f" p4 p1))
            (if (/= p6sel nil)(command "break" p6 "f" p6 p1))
            (c:lst1)
            (cond
                ((= ghk 150)
                    (command "insert" "*c:/ghk/dwg/e45d150" p1 "1" ang1)
                    (if (= peldn45-t 1)
                        (command "mirror" (ss-add) "" p1 p4 "y")
                    )
                )
                ((= ghk 200)
                    (command "insert" "*c:/ghk/dwg/e45d200" p1 "1" ang1)
                    (if (= peldn45-t 1)
                        (command "mirror" (ss-add) "" p1 p4 "y")
                    )
                )
                ((= ghk 250)
                    (command "insert" "*c:/ghk/dwg/e45d250" p1 "1" ang1)
                    (if (= peldn45-t 1)
                        (command "mirror" (ss-add) "" p1 p4 "y")
                    )
                )
                ((= ghk 300)
                    (command "insert" "*c:/ghk/dwg/e45d300" p1 "1" ang1)
                    (if (= peldn45-t 1)
                        (command "mirror" (ss-add) "" p1 p4 "y")
                    )
                )
                ((= ghk 350)
                    (command "insert" "*c:/ghk/dwg/e45d350" p1 "1" ang1)
                    (if (= peldn45-t 1)
                        (command "mirror" (ss-add) "" p1 p4 "y")
                    )
                )
                ((= ghk 400)
                    (command "insert" "*c:/ghk/dwg/e45d400" p1 "1" ang1)
                    (if (= peldn45-t 1)
                        (command "mirror" (ss-add) "" p1 p4 "y")
                    )
                )
                ((= ghk 450)
                    (command "insert" "*c:/ghk/dwg/e45d450" p1 "1" ang1)
                    (if (= peldn45-t 1)
                        (command "mirror" (ss-add) "" p1 p4 "y")
                    )
                )
                ((= ghk 500)
                    (command "insert" "*c:/ghk/dwg/e45d500" p1 "1" ang1)
                    (if (= peldn45-t 1)
                        (command "mirror" (ss-add) "" p1 p4 "y")
                    )
                )
            )
        )
    )
    (setq peldn45-t nil)
    (pse2)
)
