;; Name   : Pipe
;; Date   : 1997. 1. 17
;; By     : Kim Gihun, Kiryung eng'g CO., LTD.
;; Subject: Pipe plan,pipe sect hatch1,pipe sect, pipe insu.,pipe jump,cap,subpipe
;;;;;; pipe ( A-1 )
(defun pipe(/ p1 p2 ang)
    (pse1)
    (setvar "osmode" 33)
    (setq p1 (GETPOINT "\n     PICK START POINT OF PIPE : "))
    (setvar "osmode" 0)
    (setq p2 (GETPOINT p1 "\n     PICK END POINT OF PIPE : "))
    (setq ang (angle p1 p2))
    (p-data1)
    (ls3)           ;layer set (ghk.lsp)
    (command "line" (polar p1 (+ ang (dtr 90))  piphd) (polar p2 (+ ang (dtr 90))  piphd) "" )
    (command "line" (polar p1 (+ ang (dtr 270)) piphd) (polar p2 (+ ang (dtr 270)) piphd) "" )
    (command "layer" "s" "1E" "")
    (command "line" p1 p2 "")
    (pse2)
)
;;;;;;Front pipe section (hatch1) lisp ( A-3 )
(defun pipep(/ p1 p2 ang p4sel p3 p4 p5 p6 p7 p8 p9 p10 p11)
    (pse1)
    (setvar "osmode" 33)
    (setq p1 (GETPOINT "\n     PICK START POINT OF PIPE : "))
    (setvar "osmode" 0)
    (setq p2 (GETPOINT p1 "\n     PICK END POINT OF PIPE : "))
    (setq ang (angle p1 p2))
    (setq p4sel nil)
    (p-data1)
    (subpipe2)
    (if (= radu- "S")(subpipe p1 ang elbow90s)(subpipe p1 ang elbow90l))
    (setq p4sel(ssget p4))
    (subpipe1)
    (command "layer" "s" "2C" "")
    (c:lst1)
    (command "pline" p10 "a" "r" (/ piphd 2.00) p1 p11 "s" p4 p10 "")
    (command "layer" "s" "1C" "")
    (if (< ghk large)
        (command "hatch" "ansi31" (* s 7) "0" (ss-add) "")
        (command "hatch" "ansi31" (* s 10) "0" (ss-add) "")
    )
    (subpipe3)
    (command "layer" "s" "1E" "")
    (command "line" p3 p4 "" "line" p5 p6 "")
    (if (/= withval nil)
        (endconn-val p7 ang)
        (endconn-flg p7 ang)
    )
    (pse2)
)
;;;;;;Front pipe section lisp ( A-2 )
(defun pipes(/ p1 p2 ang p4sel p3 p4 p5 p6 p7 p8 p9 p10 p11)
    (pse1)
    (setvar "osmode" 33)
    (setq p1 (GETPOINT "\n     PICK START POINT OF PIPE : "))
    (setvar "osmode" 0)
    (setq p2 (GETPOINT p1 "\n     PICK END POINT OF PIPE : "))
    (setq ang (angle p1 p2))
    (setq p4sel nil)
    (p-data1)
    (subpipe2)
    (if (= radu- "S")(subpipe p1 ang elbow90s)(subpipe p1 ang elbow90l))
    (setq p4sel(ssget p4))
    (if (not entt-ch1)(load"c:/ghk/lsp/elbow"))
    (subpipe1)
    (command "layer" "s" "1C" "")
    (if (< ghk large)
        (command "hatch" "ansi31" (* s 7) "0" (ss-add) "")
        (command "hatch" "ansi31" (* s 10) "0" (ss-add) "")
    )
    (subpipe3)
    (command "layer" "s" "1E" "")
    (command "line" p3 p4 "" "line" p5 p6 "")
    (if (/= withval nil)
        (endconn-val p7 ang)
        (endconn-flg p7 ang)
    )
    (pse2)
)
;;;;;;Front pipe jump lisp ( A-5 )
(defun linejump (/ p1 p2 ang p3 p4 p5 p6 p7 p8 p9)
    (pse1)
    (setvar "osmode" 33)
    (setq p1 (GETPOINT "\n     PICK START POINT OF PIPE : "))
    (setvar "osmode" 0)
    (setq p2 (GETPOINT p1 "\n     PICK END POINT OF PIPE : "))
    (setq ang (angle p1 p2))
    (p-data2)
    (setq p3 (polar p1 (+ ang (dtr 90)) (/ piphd 2)))
    (setq p4 (polar p1 (+ ang (dtr 90)) piphd))
    (setq p5 (polar p1 (+ ang (dtr 270)) (/ piphd 2)))
    (setq p6 (polar p1 (+ ang (dtr 270)) piphd))
    (setq p7 (polar p3 (+ ang (dtr 180)) (/ piphd 6)))
    (setq p8 (polar p5 (+ ang (dtr 180)) (/ piphd 6)))
    (setq p9 (polar p5 ang (/ piphd 6)))
    (command "layer" "s" "2C" "")
    (command "arc" p4 p7 p1)
    (command "arc" p1 p8 p6)
    (command "arc" p6 p9 p1)
    (pse2)
)
;;;;;;cap lisp ( B-4 )
(defun caplsp (/ p1 p2 ang p3 p4 p5 pt1 pt2 pt3 pt4 pt5)
    (pse1)
    (setvar "osmode" 33)
    (setq p1 (GETPOINT "\n     PICK START POINT OF PIPE : "))
    (setvar "osmode" 0)
    (setq p2 (GETPOINT p1 "\n     PICK END POINT OF PIPE : "))
    (setq ang (angle p1 p2))
    (p-data1)
    (setq p3  (polar p1 (+ ang (dtr 180)) cap))
    (setq p4  (polar p1 (+ ang (dtr 270)) piphd))
    (setq p5  (polar p1 (+ ang (dtr 90)) piphd))
    (setq pt1 (polar p1 (+ ang (dtr 180)) (/ piphd 3)))
    (setq pt2 (polar pt1 (+ ang (dtr 270)) piphd))
    (setq pt3 (polar pt1 (+ ang (dtr 90)) piphd))
    (setq pt4 (polar pt2 ang cap))
    (setq pt5 (polar pt3 ang cap))
    (ls2)
    (if (< ghk sock)
        (command "line" pt4 pt2 pt3 pt5 "")
        (progn
            (command "arc" p5 p3 p4)
            (command "line" p4 p5 "")
        )
    )
    (pse2)
)
;;;;;;;;;;;;;;;p1    ang   distance
(defun subpipe(pipe1 pipe2 pipe3 / )
    (if (= withins "ON")
        (progn
            (setq p3 (polar pipe1 (+ pipe2 (dtr 180)) (* 1.1 insul)))
            (setq p5 (polar pipe1 (+ pipe2 (dtr 90)) (* 1.1 insul)))
            (setq p6 (polar pipe1 (- pipe2 (dtr 90)) (* 1.1 insul)))
        )
        (progn
            (setq p3 (polar pipe1 (+ pipe2 (dtr 180)) (* 1.3 piphd)))
            (setq p5 (polar pipe1 (+ pipe2 (dtr 90)) (* 1.3 piphd)))
            (setq p6 (polar pipe1 (- pipe2 (dtr 90)) (* 1.3 piphd)))
        )
    )
    (setq p4 (polar pipe1 pipe2 piphd))
    (setq p7 (polar pipe1 pipe2 pipe3))
    (setq p8 (polar p7 (+ pipe2 (dtr 90)) piphd))
    (setq p9 (polar p7 (+ pipe2 (dtr 270)) piphd))
    (setq p10 (polar pipe1 (+ pipe2 (dtr 90))  piphd))
    (setq p11 (polar pipe1 (+ pipe2 (dtr 270))  piphd))
)
(defun subpipe1()
    (endconn-flg p7 ang)
    (if (< ghk sock)
        (progn
            (command "layer" "s" "5C" "")
            (if (/= p4sel nil)
                (entt-ch1 p4sel p1 p4)
                (command "line" p4 p7 "")
            )
            (command "line" p8 p9 "")
            (command "layer" "s" "3C" "")
            (c:lst1)
            (command "circle" p1 piphd)
        )
        (if (< ghk large)
            (progn
                (weld-mark p7)
                (command "layer" "s" "5C" "")
                (if (/= p4sel nil)
                    (entt-ch1 p4sel p1 p4)
                    (command "line" p4 p7 "")
                )
                (command "layer" "s" "3C" "")
                (c:lst1)
                (command "circle" p1 piphd)
            )
            (if (< ghk double)
                (progn
                    (weld-mark p7)
                    (command "layer" "s" "8C" "")
                    (if (/= p4sel nil)
                        (entt-ch1 p4sel p1 p4)
                        (command "line" p4 p7 "")
                    )
                    (command "layer" "s" "5C" "")
                    (c:lst1)
                    (command "circle" p1 piphd)
                )
                (progn
                    (command "layer" "s" "5C" "")
                    (command "line" p10 p8 p9 p11 "")
                    (c:lst1)
                    (command "circle" p1 piphd)
                )
            )
        )
    )
)
(defun subpipe2()
    (if (= withins "ON")
        (progn
            (if (not in-thk)(setq in-thk 50))
            (prompt "\n     Do you want insulation thickness < ")
            (princ in-thk)
            (prompt " t> : ")
            (setq insul(getint ""))
            (if (= insul nil)(setq insul in-thk)(setq in-thk insul))
            (setq insul(+ piphd insul))
        )
    )
)
(defun subpipe3()
    (if (= withins "ON")
        (progn
            (c:lst1)
            (command "circle" p1 insul)
            (command "circle" p1 piphd)
            (command "layer" "s" "1C" "")
            (command "hatch" "dots,o" (* s (if (< ghk large) 7 (if (< ghk double) 10 20))) "0" (ss-add) "")
            (command "erase" "p" "")
            (command "layer" "s" "2C" "")
            (command "circle" p1 insul)
        )
    )
)
