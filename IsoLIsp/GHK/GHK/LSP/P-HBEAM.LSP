(defun c:p-hbeam(/ dcl_id lst2 lst1 hs- lst2- lst21- tt lst22- lst23- hh
                  hb ht1 ht2 hr u-wt)
 (pse1)
 (setq dcl_id (load_dialog "c:/ghk/lsp/hbeam.dcl"))
 (if (not (new_dialog "hbeam" dcl_id))
     (exit)
 )
 (if (or (= ta1 4) (= ta1 5) (= ta1 6))
    (p-data "p-ibeam")
    (p-data "p-hbeam")
 )
 (if (= l-type 0)
    (set_tile "zline" "1")
    (set_tile "zpline" "1")
 )
 (if (not hbeamnum1)
    (progn
        (setq hbeamnum1 "0")
        (setq hs- (nth 0 lst2))
        (setq lst2- (nth 0 lst1))
        (setq lst21- (nth 0 lst2-))
        (setq tt(nth 0 lst21-))
        (setq lst22- (nth 1 lst2-))
    )
    (progn
        (setq hs- (nth (atoi hbeamnum1) lst2))
        (setq lst2- (nth (atoi hbeamnum1) lst1))
        (setq lst21- (nth 0 lst2-))
        (setq tt(nth 0 lst21-))
        (setq lst22- (nth 1 lst2-))
    )
 )
 (if (not hbeamnum2)
    (progn
        (setq hbeamnum2 "0")
        (setq lst23- (nth 0 lst22-))
    )
    (progn
        (setq lst23- (nth (atoi hbeamnum2) lst22-))
        (if (= lst23- nil)(setq lst23- (nth 0 lst22-)))
    )
 )
 (if (= h-type 0)
    (setq hh(nth 0 lst23-) hb(nth 1 lst23-) ht1(nth 2 lst23-)
        ht2(nth 3 lst23-) hr1(nth 4 lst23-)  hr2(nth 5 lst23-)
        hr2(nth 5 lst23-)
    )
    (setq hh(nth 0 lst23-) hb(nth 1 lst23-) ht1(nth 2 lst23-)
        ht2(nth 3 lst23-) hr1(nth 4 lst23-) hr2(nth 5 lst23-)
    )
 )
 (action_tile "hs"   "(hs_1 (setq hbeamnum1 $value))")
 (action_tile "thk"  "(hs_2 (setq hbeamnum2 $value))")
 (action_tile "zpline" "(setq l-type 0)")
 (action_tile "zline"  "(setq l-type 1)")
 (action_tile "zhh"  "(setq hh $value)")
 (action_tile "zhb"  "(setq hb $value)")
 (action_tile "zt1"  "(setq ht1 $value)")
 (action_tile "zt2"  "(setq ht2 $value)")
 (action_tile "zhr1"  "(setq hr1 $value)")
 (action_tile "zhr2"  "(setq hr2 $value)")
 (start_list "hs")
 (mapcar 'add_list lst2)
 (end_list)
 (start_list "thk")
 (mapcar 'add_list lst21-)
 (end_list)
 (set_tile "hs"  hbeamnum1)
 (set_tile "thk" hbeamnum2)
 (set_tile "zhs" hs-)
 (set_tile "zhh" hh)
 (set_tile "zhb" hb)
 (set_tile "zt1" ht1)
 (set_tile "zt2" ht2)
 (set_tile "zhr2" hr2)
 (setq ok(start_dialog))
 (done_dialog)
 (unload_dialog dcl_id)
 (if (= ok 1)(hsdwg))
 (princ)
)

(defun hs_1(data)
 (setq hs- (nth (atoi data) lst2))
 (setq lst2- (nth (atoi data) lst1))
 (setq lst21- (nth 0 lst2-))
 (setq lst22- (nth 1 lst2-))
 (setq lst23- (nth 0 lst22-))
 (setq hh(nth 0 lst23-) hb(nth 1 lst23-)
       ht2(nth 3 lst23-) hr1(nth 4 lst23-) hr2(nth 5 lst23-)
 )
 (start_list "thk")
 (mapcar 'add_list lst21-)
 (end_list)
 (set_tile "thk" hbeamnum2)
 (set_tile "zhs" hs-)
 (set_tile "zhh" hh)
 (set_tile "zhb" hb)
 (set_tile "zt1" ht1)
 (set_tile "zt2" ht2)
 (set_tile "zhr1" hr1)
 (set_tile "zhr2" hr2)
)

(defun hs_2(data)
 (setq lst23- (nth (atoi data) lst22-))
 (setq ht1(nth 2 lst23-) ht2(nth 3 lst23-) hr1(nth 4 lst23-) hr2(nth 5 lst23-)
 )
 (set_tile "zhh" hh)
 (set_tile "zhb" hb)
 (set_tile "zt1" ht1)
 (set_tile "zt2" ht2)
 (set_tile "zhr1" hr1)
 (set_tile "zhr2" hr2)
)
;;;;;;shell nozzzle lisp
(defun hsdwg(/ sca snpt1 snpt2 ang)
    (command "osmode" "33")
    (command "orthomode" "1")
    (setq snpt1 (getpoint "Start point :"))(terpri)
    (setvar "osmode" 0)
    (setq snpt2 (getpoint snpt1 "Select pipe line :"))
    (setq ang (angle snpt1 snpt2))
    (if (= 1 ta1)
         (front)
         (if (or (= 2 ta1) (= 5 ta1))
            (side)
            (if (or (= 3 ta1) (= 6 ta1))
                (top)
                (if (= 4 ta1)
                    (i-front)
                )
            )
         )
    )
;;;val. return
 (pse2)
)

(defun front(/ c1 c2 c3 c4 p3 p31 p4 p41 p5 p51 p6 p61 p7 p71 p8 p81
               pt4 pt41 pt5 pt51 pt6 pt61 pt7 pt71 pt8 pt81 )
    (setq C1  (polar snpt1 (+ ang (dtr 90)) (* (atof hh) 0.7)))
    (setq C2  (polar snpt1 (+ ang (dtr 270)) (* (atof hh) 0.7)))
    (setq C3  (polar snpt1 ang (* (atof hb) 0.6)))
    (setq C4  (polar snpt1 (+ ang (dtr 180)) (* (atof hb) 0.6)))
    (setq p3  (polar snpt1 ang (/ (atof ht1) 2)))
    (setq p31 (polar snpt1 (+ ang (dtr 180)) (/ (atof ht1) 2)))
    (setq p4  (polar p3 (+ ang (dtr 90)) (- (/ (atof hh) 2) (+ (atof hr1) (atof ht2)))))
    (setq p41 (polar p31 (+ ang (dtr 90)) (- (/ (atof hh)  2)(+ (atof hr1) (atof ht2)))))
    (setq p5  (polar p4 ang (atof hr1)))
    (setq p51 (polar p41 (+ ang (dtr 180)) (atof hr1)))
    (setq p6  (polar p5 (+ ang (dtr 90)) (atof hr1)))
    (setq p61 (polar p51 (+ ang (dtr 90)) (atof hr1)))
    (setq p7  (polar p6 ang (- (/ (atof hb) 2)(+ (atof hr1) (/ (atof ht1) 2)))))
    (setq p71 (polar p61 (+ ang (dtr 180)) (- (/ (atof hb) 2)(+ (atof hr1) (/ (atof ht1) 2)))))
    (setq p8  (polar p7 (+ ang (dtr 90)) (atof ht2)))
    (setq p81  (polar p71 (+ ang (dtr 90)) (atof ht2)))
    (setq pt4  (polar p3 (+ ang (dtr 270)) (- (/ (atof hh) 2) (+ (atof hr1) (atof ht2)))))
    (setq pt41 (polar p31 (+ ang (dtr 270)) (- (/ (atof hh)  2)(+ (atof hr1) (atof ht2)))))
    (setq pt5  (polar pt4 ang (atof hr1)))
    (setq pt51 (polar pt41 (+ ang (dtr 180)) (atof hr1)))
    (setq pt6  (polar pt5 (+ ang (dtr 270)) (atof hr1)))
    (setq pt61 (polar pt51 (+ ang (dtr 270)) (atof hr1)))
    (setq pt7  (polar pt6 ang (- (/ (atof hb) 2)(+ (atof hr1) (/ (atof ht1) 2)))))
    (setq pt71 (polar pt61 (+ ang (dtr 180)) (- (/ (atof hb) 2)(+ (atof hr1) (/ (atof ht1) 2)))))
    (setq pt8  (polar pt7 (+ ang (dtr 270)) (atof ht2)))
    (setq pt81  (polar pt71 (+ ang (dtr 270)) (atof ht2)))
    (command "layer" "s" "2c" "")
    (if (= l-type 1)
        (progn
            (command "line" p4 pt4 "")
            (command "line" p41 pt41 "")
            (command "line" p6 p7 p8 p81 p71 p61 "")
            (command "line" pt6 pt7 pt8 pt81 pt71 pt61 "")
            (command "arc" "c" p5 p6 p4)
            (command "arc" "c" p51 p41 p61)
            (command "arc" "c" pt5 pt4 pt6)
            (command "arc" "c" pt51 pt61 pt41)
        )
        (progn
            (command "pline" p8 "w" (* s 0.5) (* s 0.5) p81 "")
            (command "pline" pt8 "w" (* s 0.5) (* s 0.5) pt81 "")
            (command "pline" (polar snpt1 (+ ang (dtr 90)) (* (atof hh) 0.5)) "w" (* s 0.5) (* s 0.5) (polar snpt1 (+ ang (dtr 270)) (* (atof hh) 0.5)) "")
        )
    )
    (command "layer" "s" "1e" "")
    (command "line" C1 C2 "")
    (command "line" C3 C4 "")
)

(defun side(/ p3 p31 p4 p41 pt3 pt31 pt4 pt41)
    (setq p3  (polar snpt1 (+ ang (dtr 90)) (- (/ (atof hh) 2) (atof ht2))))
    (setq p31  (polar snpt1 (+ ang (dtr 270)) (- (/ (atof hh) 2) (atof ht2))))
    (setq p4  (polar snpt1 (+ ang (dtr 90)) (/ (atof hh) 2)))
    (setq p41  (polar snpt1 (+ ang (dtr 270)) (/ (atof hh) 2)))
    (setq pt3  (polar snpt2 (+ ang (dtr 90)) (- (/ (atof hh) 2) (atof ht2))))
    (setq pt31  (polar snpt2 (+ ang (dtr 270)) (- (/ (atof hh) 2) (atof ht2))))
    (setq pt4  (polar snpt2 (+ ang (dtr 90)) (/ (atof hh) 2)))
    (setq pt41  (polar snpt2 (+ ang (dtr 270)) (/ (atof hh) 2)))
    (command "layer" "s" "2c" "")
    (command "line" p3 pt3 "")
    (command "line" p31 pt31 "")
    (command "line" p4 pt4 "")
    (command "line" p41 pt41 "")
    (command "line" p4 p41 "")
    (command "line" pt4 pt41 "")
    (command "layer" "s" "1E" "")
    (command "line" snpt1 snpt2 "")
)

(defun top(/  p3 p31 p4 p41 pt3 pt31 pt4 pt41)
    (setq p3  (polar snpt1 (+ ang (dtr 90))    (/ (atof ht1) 2)))
    (setq p31  (polar snpt1 (+ ang (dtr 270))  (/ (atof ht1) 2)))
    (setq p4  (polar snpt1 (+ ang (dtr 90))    (/ (atof hb) 2)))
    (setq p41  (polar snpt1 (+ ang (dtr 270))  (/ (atof hb) 2)))
    (setq pt3  (polar snpt2 (+ ang (dtr 90))   (/ (atof ht1) 2)))
    (setq pt31  (polar snpt2 (+ ang (dtr 270)) (/ (atof ht1) 2)))
    (setq pt4  (polar snpt2 (+ ang (dtr 90))   (/ (atof hb) 2)))
    (setq pt41  (polar snpt2 (+ ang (dtr 270)) (/ (atof hb) 2)))
    (command "layer" "s" "2c" "")
    (command "line" p4 pt4 "")
    (command "line" p41 pt41 "")
    (command "line" p4 p41 "")
    (command "line" pt4 pt41 "")
    (command "layer" "s" "2h" "")
    (command "line" p3 pt3 "")
    (command "line" p31 pt31 "")
    (command "layer" "s" "1E" "")
    (command "line" snpt1 snpt2 "")
)
(defun i-front(/ c1 c2 c3 c4 p3 p31 p4 p41 p5 p51 p6 p61 p7 p71 p9 p91
                 p10 p10a p8 p81 pt4 pt41 pt5 pt51 pt6 pt61 pt7 pt71
                 pt8 pt81 pt9 pt91 pt10 pt10a)
    (setq C1  (polar snpt1 (+ ang (dtr 90))    (* (atof hh) 0.7)))
    (setq C2  (polar snpt1 (+ ang (dtr 270))   (* (atof hh) 0.7)))
    (setq C3  (polar snpt1 ang (* (atof hb) 0.6)))
    (setq C4  (polar snpt1 (+ ang (dtr 180)) (* (atof hb) 0.6)))
    (setq p3  (polar snpt1 ang      (/ (atof ht1) 2)))
    (setq p31 (polar snpt1 (+ ang (dtr 180))   (/ (atof ht1) 2)))
    (setq p4  (polar p3 (+ ang (dtr 90))       (- (/ (atof hh) 2) (+ (atof hr1) (atof ht2)))))
    (setq p41 (polar p31 (+ ang (dtr 90))      (- (/ (atof hh) 2) (+ (atof hr1) (atof ht2)))))
    (setq p5  (polar p4 ang         (atof hr1)))
    (setq p51 (polar p41 (+ ang (dtr 180))     (atof hr1)))
    (setq p6  (polar p5 (+ ang (dtr 90))       (atof hr1)))
    (setq p61 (polar p51 (+ ang (dtr 90))      (atof hr1)))
    (setq p7  (polar p6 ang         (- (/ (atof hb) 2)(+ (atof hr1) (atof hr2) (/ (atof ht1) 2)))))
    (setq p71 (polar p61 (+ ang (dtr 180))     (- (/ (atof hb) 2)(+ (atof hr1) (atof hr2) (/ (atof ht1) 2)))))
    (setq p9  (polar p7 (+ ang (dtr 90))       (atof hr2)))
    (setq p91 (polar p71 (+ ang (dtr 90))      (atof hr2)))
    (setq p10 (polar p9 ang         (atof hr2)))
    (setq p10a (polar p91 (+ ang (dtr 180))    (atof hr2)))
    (setq p8   (polar p10 (+ ang (dtr 90))     (- (atof ht2) (atof hr2))))
    (setq p81  (polar p10a (+ ang (dtr 90))    (- (atof ht2) (atof hr2))))
    (setq pt4  (polar p3 (+ ang (dtr 270))     (- (/ (atof hh) 2) (+ (atof hr1) (atof ht2)))))
    (setq pt41 (polar p31 (+ ang (dtr 270))    (- (/ (atof hh)  2)(+ (atof hr1) (atof ht2)))))
    (setq pt5  (polar pt4 ang       (atof hr1)))
    (setq pt51 (polar pt41 (+ ang (dtr 180))   (atof hr1)))
    (setq pt6  (polar pt5 (+ ang (dtr 270))    (atof hr1)))
    (setq pt61 (polar pt51 (+ ang (dtr 270))   (atof hr1)))
    (setq pt7  (polar pt6 ang       (- (/ (atof hb) 2)(+ (atof hr1) (atof hr2) (/ (atof ht1) 2)))))
    (setq pt71 (polar pt61 (+ ang (dtr 180))   (- (/ (atof hb) 2)(+ (atof hr1) (atof hr2) (/ (atof ht1) 2)))))
    (setq pt9  (polar pt7 (+ ang (dtr 270))    (atof hr2)))
    (setq pt91 (polar pt71 (+ ang (dtr 270))   (atof hr2)))
    (setq pt10 (polar pt9 ang       (atof hr2)))
    (setq pt10a (polar pt91 (+ ang (dtr 180))  (atof hr2)))
    (setq pt8   (polar pt10 (+ ang (dtr 270))  (- (atof ht2) (atof hr2))))
    (setq pt81  (polar pt10a (+ ang (dtr 270)) (- (atof ht2) (atof hr2))))
    (command "layer" "s" "2c" "")
    (if (= l-type 1)
        (progn
            (command "line" p4 pt4 "")
            (command "line" p41 pt41 "")
            (command "line" p6 p7 "")
            (command "line" p61 p71 "")
            (command "line" pt6 pt7 "")
            (command "line" pt61 pt71 "")
            (command "line" p10 p8 p81 p10a "")
            (command "line" pt10 pt8 pt81 pt10a "")
            (command "arc" "c" p9 p7 p10)
            (command "arc" "c" p91 p10a p71)
            (command "arc" "c" p5 p6 p4)
            (command "arc" "c" p51 p41 p61)
            (command "arc" "c" pt5 pt4 pt6)
            (command "arc" "c" pt51 pt61 pt41)
            (command "arc" "c" pt9 pt10 pt7)
            (command "arc" "c" pt91 pt71 pt10a)
        )
        (progn
            (command "pline" p8 "w" (* s 0.5) (* s 0.5) p81 "")
            (command "pline" pt8 "w" (* s 0.5) (* s 0.5) pt81 "")
            (command "pline" (polar snpt1 (+ ang (dtr 90)) (* (atof hh) 0.5)) "w" (* s 0.5) (* s 0.5) (polar snpt1 (+ ang (dtr 270)) (* (atof hh) 0.5)) "")
        )
    )
    (command "layer" "s" "1E" "")
    (command "line" C1 C2 "")
    (command "line" C3 C4 "")
)
