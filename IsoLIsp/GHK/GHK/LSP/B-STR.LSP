;<<<<<<<<<<<<<<<<<<<<<<<< AUTO CAD LISP >>>>>>>>>>>>>>>>>>>>>>>>>>>>>>>
;~~~~~~~~~~~~~~~~B-TYPE STRAINER (WELD NECK) SIDE LISP~~~~~~~~~~~~~~~~~
;
(defun b-strf ()
    (b-strain)
;<<<<<<<<<<<<<<<<<<< strainer dwg>>>>>>>>>>>>>>>>>>>>>>>>>>>>>>>>>>>>>>>>>
    (command "layer" "s" "2C" "")
    (command "pline" s2b "w" "0" "0" s3a s31 s22 s2a s1a s11 s21 s22 "")
    (command "pline" st2b "w" "0" "0" st3a st31 st22 st2a st1a st11 st21 st22 "")
    (command "pline" s4b3 "w" "0" "0" s4c1 s4c2 s4b4 s4b1 s4d1 s4d2 s4b2 s4b4 "")
    (command "line" s4a1 s4a2 "" "line" s3a s5a s4c1 "" "line" st3a s6a s4c2 "")
    (command "line" s31 s51 s52 s62 s61 st31 "")
    (command "layer" "s" "1P" "")
    (command "line" s4d3 s4d5 s4d4 s4d6 s4d5 "" "line" s4d3 s4d6 "")
    (command "layer" "s" "1E" "")
    (command "line" sfcen1 sfcen2 "")
    (setq bstr-t nil)
    (pse2)
)
;~~~~~~~~~~~~~~~~~~~B-TYPE STRAINER (WELD NECK) TOP LISP~~~~~~~~~~~~~~~~~~~~~
;;( C-9 )
(defun b-strt ()
    (b-strain)
;<<<<<<<<<<<<<<<<<<< strainer dwg>>>>>>>>>>>>>>>>>>>>>>>>>>>>>>>>>>>>>>>>>
    (command "layer" "s" "2C" "")
    (command "pline" s2b "w" "0" "0" s3a s31 s22 s2a s1a s11 s21 s22 "")
    (command "pline" st2b "w" "0" "0" st3a st31 st22 st2a st1a st11 st21 st22 "")
    (command "line" s3a st3a "")
    (command "line" s31 st31 "")
    (command "circle" s4 "d" (* flgd 1.33))
    (command "layer" "s" "2H" "")
    (command "circle" s4 "d" (* pipd 1.33))
    (command "layer" "s" "1E" "")
    (command "line" stcen1 stcen2 "")
    (setq bstr-t nil)
    (pse2)
)
;~~~~~~~~~~~~~~~~~~~B-TYPE STRAINER (WELD NECK) SECTION LISP~~~~~~~~~~~~~~~~~~
;;( C-10 )
(defun b-strs ()
    (b-strain)
;<<<<<<<<<<<<<<<<<<< strainer dwg>>>>>>>>>>>>>>>>>>>>>>>>>>>>>>>>>>>>>>>>>
    (command "layer" "s" "2C" "")
    (command "pline" s4b3 "w" "0" "0" s4c1 s4c2 s4b4 s4b1 s4d1 s4d2 s4b2 s4b4 "")
    (command "line" s4c1 s52 s62 s4c2 "")
    (command "circle" s4 "d" flgd)
    (command "circle" s4 "d" pipd)
    (command "layer" "s" "1P" "")
    (command "line" s4d3 s4d5 s4d4 s4d6 s4d5 "")
    (command "line" s4d3 s4d6 "")
    (command "layer" "s" "1E" "")
    (command "line" sfcen1 sfcen2 "")
    (command "line" sscen1 sscen2 "")
    (setq bstr-t nil)
    (pse2)
)
;<<<<<<<<<<<<<<<<<<< strainer dwg>>>>>>>>>>>>>>>>>>>>>>>>>>>>>>>>>>>>>>>>>
(defun b-strain ()
    (setq s1   (polar p2 ang g))
    (setq s1a  (polar s1 (+ ang (dtr 90)) flghd))
    (setq s11  (polar s1 (+ ang (dtr 270)) flghd))
    (setq s2   (polar s1 ang flgthk))
    (setq s2a  (polar s1a ang flgthk))
    (setq s2b  (polar s2 (+ ang (dtr 90)) (/ hubdia 2)))
    (setq s2c  (polar s2 (+ ang (dtr 90)) piphd))
    (setq s21  (polar s11 ang flgthk))
    (setq s22  (polar s2 (+ ang (dtr 270)) (/ hubdia 2)))
    (setq s23  (polar s2 (+ ang (dtr 270)) piphd))
    (setq s3   (polar s1 ang flglen))
    (setq s3a  (polar s3 (+ ang (dtr 90)) piphd))
    (setq s31  (polar s3 (+ ang (dtr 270)) piphd))
    (setq s4   (polar p2 ang (/ len 2)))
    (setq sfcen1(polar s4 (+ ang (dtr 90)) (* vall2 1.1)))
    (setq sfcen2(polar s4 (+ ang (dtr 270)) (* vall1 1.1)))
    (setq stcen1(polar s4 (+ ang (dtr 90)) (*  flghd 1.7)))
    (setq stcen2(polar s4 (+ ang (dtr 270)) (*  flghd 1.7)))
    (setq sscen1(polar s4 ang (* flgd 1.3)))
    (setq sscen2(polar s4 (+ ang (dtr 180)) (* flgd 1.3)))
    (setq s4a  (polar s4 (+ ang (dtr 90)) vall2))
    (setq s4a1 (polar s4a (+ ang (dtr 180)) (* flghd 1.33)))
    (setq s4a2 (polar s4a ang (* flghd 1.33)))
    (setq s4b  (polar s4a (+ ang (dtr 270)) flgthk))
    (setq s4b1 (polar s4b (+ ang (dtr 180)) (* flghd 1.33)))
    (setq s4b2 (polar s4b ang (* flghd 1.33)))
    (setq s4b3 (polar s4b (+ ang (dtr 180)) (* (/ hubdia 2) 1.33)))
    (setq s4b4 (polar s4b ang (* (/ hubdia 2) 1.33)))
    (setq s4b5 (polar s4b (+ ang (dtr 180)) (/ (* hubdia 1.33) 2)))
    (setq s4b6 (polar s4b ang (/ (* hubdia 1.33) 2)))
    (setq s4c  (polar s4a (+ ang (dtr 270)) flglen))
    (setq s4c1 (polar s4c (+ ang (dtr 180)) (/ (* pipd 1.33) 2)))
    (setq s4c2 (polar s4c ang (/ (* pipd 1.33) 2)))
    (setq s4d  (polar s4a (+ ang (dtr 90)) flgthk))
    (setq s4d1 (polar s4d (+ ang (dtr 180)) (* flghd 1.33)))
    (setq s4d2 (polar s4d ang (* flghd 1.33)))
    (setq s4d3 (polar s4d (+ ang (dtr 180)) (/ (* hubdia 1.33) 2)))
    (setq s4d4 (polar s4d ang (/ (* hubdia 1.33) 2)))
    (setq s4d5 (polar s4d3 (+ ang (dtr 90)) vall1))
    (setq s4d6 (polar s4d4 (+ ang (dtr 90)) vall1))
    (setq s5   (polar s4 (+ ang (dtr 180)) (/ (* pipd 1.33) 2)))
    (setq s5a  (polar s5 (+ ang (dtr 90)) piphd))
    (setq s51  (polar s5 (+ ang (dtr 270)) piphd))
    (setq s52  (polar s5 (+ ang (dtr 270)) vall1))
    (setq s6   (polar s4 ang (/ (* pipd 1.33) 2)))
    (setq s6a  (polar s6 (+ ang (dtr 90)) piphd))
    (setq s61  (polar s6 (+ ang (dtr 270)) piphd))
    (setq s62  (polar s6 (+ ang (dtr 270)) vall1))
    (setq st1   (polar p2 ang (- len g)))
    (setq st1a  (polar st1 (+ ang (dtr 90)) flghd))
    (setq st11  (polar st1 (+ ang (dtr 270)) flghd))
    (setq st2   (polar st1 (+ ang (dtr 180)) flgthk))
    (setq st2a  (polar st1a (+ ang (dtr 180)) flgthk))
    (setq st2b  (polar st2 (+ ang (dtr 90)) (/ hubdia 2)))
    (setq st2c  (polar st2 (+ ang (dtr 90)) piphd))
    (setq st21  (polar st11 (+ ang (dtr 180)) flgthk))
    (setq st22  (polar st2 (+ ang (dtr 270)) (/ hubdia 2)))
    (setq st23  (polar st2 (+ ang (dtr 270)) piphd))
    (setq st3   (polar st1 (+ ang (dtr 180)) flglen))
    (setq st3a  (polar st3 (+ ang (dtr 90)) piphd))
    (setq st31  (polar st3 (+ ang (dtr 270)) piphd))
)

(defun b-str (/ la orth os a-pip k-pip flglen flgd flghd flgthk hubdia
                 stubl stubl1 stubd vall vall1 vall2 len p1 p2 ang ang1
                 vall-1 s1 s1a s11 s2 s2a s2b s2c p2sel
                 s21 s22 s23 s3 s3a s31 s4 sfcenb1 sfcen2 stcen1 stcen2
                 sscen1 sscen2 s4a s4a1 s4a2 s4b s4b1 s4b2 s4b3 s4b4
                 s4b5 s4b6 s4c s4c1 s4c2 s4d s4d1 s4d2 s4d3 s4d4 s4d5
                 s4d6 s5 s5a s51 s52 s6 s6a s61 s62 st1 st1a st11 st2
                 st2a st2b st2c st21 st22 st23 st3 st3a st31)
    (pse1)
    (p-data3)
    (p-data4)
    (p-data5 "b-str")
    (endflgtype)
    (if (> vall 1)
        (progn
            (setvar "osmode" 512)
            (setq p1 (getpoint    "\nSelection point :[Default = nea point]:"))
            (setvar "osmode" 512)
            (setq p2 (getpoint p1 "\nSecond point    :[Default = nea point]:"))
            (setq p2sel(ssget p2))
            (setvar "osmode" 0)
            (setq ang (ANGLE P1  P2))
            (setq ang1 (rtd ang))
            (terpri)
            (prompt "Do you want flange to flange dimension < Default =")
            (princ vall)
            (prompt " > : ")
            (setq vall-1(getreal ""))
            (terpri)
            (if (= vall-1 nil)(setq vall vall)(setq vall vall-1))
            (if (or (= flg_end "F")(= flg_end "W")(= flg_end nil))
                (setq len (+ vall ga))
                (setq len vall)
            )
            (if (/= p2sel nil)
                (command "break" p1 "f" p2 (polar p2 ang len))
            )
            (command "layer" "s" "1E" "")
            (command "line" p2 (polar p2 ang len) "")
            (if (and (/= bstr-t 3) (or (= flg_end "F") (= flg_end "W")))
                (progn
                    (if (not val-flg)(load"c:/ghk/lsp/val-flg"))
                    (val-flg ang p2)
                    (val-flg (+ ang (dtr 180)) (polar p2 ang len))
                )
            )
            (if (= val-view 1)
                (b-strf)
                (if (= val-view 2)
                    (b-strt)
                    (if (= val-view 4)(b-strs)(b-strt)
                    )
                )
            )
        )
        (prompt "\n    IS NOT SIZE")
    )
)
