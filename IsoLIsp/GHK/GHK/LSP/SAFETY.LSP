;~~~~~~~~~~~~~~~~SAFETY VALVE SIDE LISP~~~~~~~~~~~~~~~~~
(defun safety(/ a-pip k-pip flglen flgd flgthk hubdia flghd stubl stubl1
                stubd p1 pp ang vall1 vall2 p2 p2sel v1 v2 v3 h1 h2 h3
                h4 h5 h6 h7 h8 h9)
    (pse1)
    (setvar "osmode" 32)
    (setq p1 (getpoint "\n Selection point:[Default = int point]:"))
    (setvar "osmode" 512)
    (setq pp (getpoint p1 "\n Second point:[Default = nea point]:"))
    (setvar "osmode" 0)
    (SETQ ang (ANGLE P1  Pp))
    (redsafety)
    (face-dim)
    (if (not sa-inl)(setq sa-inl 150))
    (prompt "Do you want inletflange to conter point < ")
    (princ sa-inl)
    (prompt " > : ")
    (setq vall1(getreal " "))(terpri)
    (if (or (= vall1 nil) (= vall1 "")) (setq vall1 sa-inl)(setq sa-inl vall1))
    (if (not sa-out)(setq sa-out 150))
    (prompt "Do you want outflange to conter point < ")
    (princ sa-out)
    (prompt " > : ")
    (setq vall2(getreal " "))(terpri)
    (if (or (= vall2 nil) (= vall2 "")) (setq vall2 sa-out)(setq sa-out vall2))
    (p-data3)
    (p-data4)
    (setq p2 (polar p1 (+ ang (dtr 270)) vall1))
    (setq p2sel(ssget p2))
    (if (/= p2sel nil)
        (command "break" p1 p2)
    )
    (command "layer" "s" "1E" "")
    (command "line" p1 p2 "")
    (if (not val-flg)(load"c:/ghk/lsp/val-flg"))
    (val-flg (+ ang (dtr 90)) p2)
    (setq v1 (polar p2 (+ ang (dtr 90)) g))
    (setq v2 (polar v1 ang flghd))
    (setq v3 (polar v1 (+ ang (dtr 180)) flghd))
    (setq h1 (polar p1 (+ ang (dtr 90)) (* vall1 1.2)))
    (setq h2 (polar h1 (+ ang (dtr 90)) (* vall1 0.7)))
    (setq h3 (polar h1 ang flghd))
    (setq h4 (polar h1 (+ ang (dtr 180)) flghd))
    (setq h5 (polar h3 (+ ang (dtr 90)) (* vall1 0.2)))
    (setq h6 (polar h4 (+ ang (dtr 90)) (* vall1 0.2)))
    (setq h7 (polar h5 (+ ang (dtr 90)) (* vall1 0.2)))
    (setq h8 (polar h6 (+ ang (dtr 90)) (* vall1 0.2)))
    (setq h9 (polar h7 (+ ang (dtr 90)) (* vall1 0.2)))
    (command "layer" "s" "2C" "")
    (command "pline" p1 "w" "0" "0" v2 v3 p1 "")
    (command "layer" "s" "5C" "")
    (command "line" p1 h2 "")
    (command "line" h4 h5 "")
    (command "line" h6 h7 "")
    (command "line" h8 h9 "")
    (setq ghk ghk1)
    (ch-size ghk)
    (p-data3)
    (p-data4)
    (setq p2 (polar p1 ang vall2))
    (setq p2sel(ssget p2))
    (if (/= p2sel nil)
        (command "break" p1 p2)
    )
    (command "layer" "s" "1E" "")
    (command "line" p1 p2 "")
    (val-flg (+ ang (dtr 180)) p2)
    (setq v1 (polar p2 (+ ang (dtr 180)) g))
    (setq v2 (polar v1 (+ ang (dtr 90)) flghd))
    (setq v3 (polar v1 (+ ang (dtr 270)) flghd))
    (command "layer" "s" "2C" "")
    (command "pline" p1 "w" "0" "0" v2 v3 p1 "")
    (setq ghk1 nil)
    (RESETGHK)
    (pse2)
)
;<<<<<<<<<<<<<<<<<<<<<<<< AUTO CAD LISP >>>>>>>>>>>>>>>>>>>>>>>>>>>>>>>
;~~~~~~~~~~~~~~~~SAFETY VALVE TOP LISP~~~~~~~~~~~~~~~~~
(defun safetyt (/ a-pip k-pip flglen flgd flgthk hubdia flghd stubl
                 stubl1 stubd p1 pp ang p2 p2sel flghd1 v1 v2 v3 c1 c2 c3)
    (pse1)
    (setvar "osmode" 1)
    (setq p1 (getpoint "Selection point:[Default = end point]:"))(terpri)
    (setvar "osmode" 512)
    (setq pp (getpoint p1 "Second point:[Default = nea point]:"))(terpri)
    (setvar "osmode" 0)
    (SETQ ang (ANGLE P1  Pp))
    (redsafety)
    (if (not sa-out)(setq sa-out 150))
    (prompt "Do you want outflange to conter point < ")
    (princ sa-out)
    (prompt " > : ")
    (setq vall2(getreal " "))(terpri)
    (if (or (= vall2 nil) (= vall2 "")) (setq vall2 sa-out)(setq sa-out vall2))
    (p-data4)
    (setq flghd1 flghd)
    (setq ghk ghk1)
    (ch-size ghk)
    (p-data3)
    (p-data4)
    (setq p2 (polar p1 ang vall2))
    (setq p2sel(ssget p2))
    (if (/= p2sel nil)
        (command "break" p1 p2)
    )
    (command "layer" "s" "1E" "")
    (command "line" p1 p2 "")
    (if (not val-flg)(load"c:/ghk/lsp/val-flg"))
    (val-flg (+ ang (dtr 180)) p2)
    (setq v1 (polar p2 (+ ang (dtr 180)) g))
    (setq v2 (polar v1 (+ ang (dtr 90)) flghd))
    (setq v3 (polar v1 (+ ang (dtr 270)) flghd))
    (setq c1 (polar p1 (+ ang (dtr 90)) (* flghd 1.2)))
    (setq c2 (polar p1 (+ ang (dtr 270)) (* flghd 1.2)))
    (setq c3 (polar p1 (+ ang (dtr 180)) (* flghd 1.2)))
    (ls1)
    (command "arc" "c" p1 (polar p1 (angle p1 v2) flghd1) (polar p1 (angle p1 v3) flghd1))
    (command "layer" "s" "2C" "")
    (command "pline" p1 "w" "0" "0" v2 v3 p1 "")
    (command "layer" "s" "1E" "")
    (command "line" c1 c2 "")
    (command "line" p1 c3 "")
    (command "layer" "s" la "")
    (setvar "osmode" os)
    (RESETGHK)
    (prin1)
)

(defun redsafety()
 (setq dcl_id (load_dialog "C:/GHK/LSP/redtee.dcl"))
 (if (not (new_dialog "redsafety" dcl_id))
     (exit)
 )
 (cond
     ((= ghk 25)(setq outlist (list "50")))
     ((= ghk 40)(setq outlist (list "50" "65" "80")))
     ((= ghk 50)(setq outlist (list "80")))
     ((= ghk 65)(setq outlist (list "100")))
     ((= ghk 80)(setq outlist (list "100")))
     ((= ghk 100)(setq outlist (list "150")))
     ((= ghk 150)(setq outlist (list "200" "250")))
     ((= ghk 200)(setq outlist (list "250")))
 )
 (if (= safetynum1 nil)(setq safetynum1 "0"))
 (setq ghk1(atoi (nth (atoi safetynum1) outlist)))
 (action_tile "out_size"  "(safety_1 (setq safetynum1 $value))")
 (start_list "out_size")
 (mapcar 'add_list outlist)
 (end_list)
 (setq ok(start_dialog))
 (done_dialog)
 (unload_dialog dcl_id)
 (princ)
)

(defun safety_1(data)
 (setq ghk1(atoi (nth (atoi data) outlist)))
)
