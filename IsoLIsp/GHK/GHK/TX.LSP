(defun C:TX ()
   (setq old (ssget))
   (setq typ (strcase (getstring "Change text A)ngle, H)eight,
                W)idth, or S)tyle: ")))(terpri)        
   (setq co -1)             
   (setq t2 "T")
   (cond
      ((= "H" typ)
         (setq x 40)
         (setq ht (getreal "New height: "))(terpri)
      )
      ((= "A" typ)
         (setq x 51)
         (setq ht (* pi (/ (getreal "New angle: ") 180.0)))(terpri)
      )
      ((= "W" typ)
         (setq X 41) 
         (setq ht (getreal "New width: "))(terpri)
      )
      ((= "S" typ)
         (setq x 7)
         (setq ht (getstring "New style: "))(terpri)
      )
    )
    (while (boundp 't2)
       (progn
          (setq co (1+ co))
          (setq temp (entget (ssname old co)))
          (setq oldht (assoc x temp))
          (setq newht (cons x ht))
          (setq newtext (subst newht oldht temp))
          (setq t2 (ssname old (1+ co)))
          (entmod newtext)
       )
    )
    (setq temp "FINISHED")
)
